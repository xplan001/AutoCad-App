(defun c:tt(/ s0 e e_list text_0 text_10 text_11 text_14 text_18 text_16 text_29 r a s1 e1 e1_list text_r)
  (print "刷文字角度,请选择源目标")
  (setq s0 (ssget ":s"))
  (setq e (ssname s0 0))
  (setq e_list (entget e))
  (setq text_0 (cdr(assoc 0 e_list)))
  (print "请选择要修改的文字")
  (setq s2 (ssget))
  (setq s2_long (sslength s2))
  (setq ct 0)
  (setq s1 (ssadd))
  (repeat s2_long
    (setq e2 (ssname s2 ct))
    (setq e2_list (entget e2))
    (if (= "TEXT" (cdr(assoc 0 e2_list)))
      (progn
	(ssadd e2 s1)
	(ssdel e2 s2)
	)
      (setq ct (+ ct 1))
      )
    )
  ;;;;建立文字集合s1结束
  (setq s1_long (sslength s1))
  (if (= text_0 "TEXT")
    (progn
      (setq ct 0)
      (repeat s1_long
	(setq e1 (ssname s1 ct))
        (setq e1_list (entget e1))
        (setq e1_list(subst (assoc 50 e_list) (assoc 50 e1_list) e1_list))
        (entmod e1_list)
	(setq ct (+ ct 1))
	)
      )
    (progn
      (if (= text_0 "LINE")
	(progn
	  (setq text_10 (cdr(assoc 10 e_list)))
	  (setq text_11 (cdr(assoc 11 e_list)))
	  (if (= 0 (- (car text_11) (car text_10)))
	    (setq r (/ pi 2))
	    (progn
	      (setq r (atan (/ (- (cadr text_11) (cadr text_10)) (- (car text_11) (car text_10)))))
	      (setq a (/ (* r 180) pi))
	      )
	    )
	  (setq ct 0)
	  (repeat s1_long
	    (setq e1 (ssname s1 ct))
            (setq e1_list (entget e1))
	    (setq e1_list(subst (cons 50 r) (assoc 50 e1_list) e1_list))
            (entmod e1_list)
	    (setq ct (+ ct 1))
	    )
	  )
	)
      (if (= text_0 "LWPOLYLINE")
	(progn
	  (setq text_14 (cdr(nth 14 e_list)))
          (setq text_19 (cdr(nth 18 e_list)))
	  (if (= 0 (- (car text_19) (car text_14)))
	    (setq r (/ pi 2))
	    (progn
	      (setq r (atan (/ (- (cadr text_19) (cadr text_14)) (- (car text_19) (car text_14)))))
	      (setq a (/ (* r 180) pi))
	      )
	    )
	  (setq ct 0)
	  (repeat s1_long
	    (setq e1 (ssname s1 ct))
            (setq e1_list (entget e1))
	    (setq e1_list(subst (cons 50 r) (assoc 50 e1_list) e1_list))
            (entmod e1_list)
	    (setq ct (+ ct 1))
	    )
	  )
	)
      (if (= text_0 "MLINE")
	(progn
	  (setq text_16 (cdr(nth 16 e_list)))
          (setq text_29 (cdr(nth 29 e_list)))
          (if (= 0 (- (car text_29) (car text_16)))
	    (setq r (/ pi 2))
	    (progn
	      (setq r (atan (/ (- (cadr text_29) (cadr text_16)) (- (car text_29) (car text_16)))))
	      (setq a (/ (* r 180) pi))
	      )
	    )
	  (setq ct 0)
	  (repeat s1_long
	    (setq e1 (ssname s1 ct))
            (setq e1_list (entget e1))
	    (setq e1_list(subst (cons 50 r) (assoc 50 e1_list) e1_list))
            (entmod e1_list)
	    (setq ct (+ ct 1))
	    )
	  )
	)
      )
    )
   (prin1)
  )
