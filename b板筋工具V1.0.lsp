;使用方法 
;1 板筋设置命令BJSZ，设置板的通长筋
;2 板筋过滤命令BJGL， 用于过滤计算书，生成附加钢筋文字，对于非正交的板筋按金科规定换算为正交配筋值，
;  注意对于本身通长钢筋为斜向情况时，先将计算书旋转至水平正交，再使用板筋过滤命令
;3 使用板王画板支座筋，用板王文字格式刷将生成的附加钢筋文字刷到支座钢筋上
;4 板筋改正命令BJGZ，将板王生成的斜向支座筋改正为正交钢筋
;
;未完善功能：板筋过滤对于板底筋的配筋文字生成；板筋优化BJYH 支座筋伸出长度由按梁中线计算（板王）改为按净跨计算
;插件仅支持侨恩图层，文字高度为250
;使用有问题或需要调整图层文字高度等，请联系我  
;                             by康东昌@侨恩创源 qq：714383892









;>>>>>>>>>>>>>>>>>>>>>>>>>>>>>>>>>>>>>>>>>>>>>>>>>>>>>>>>>>>>>>>>>>>>>>>>>>>>>>>>>>>>>>>>>>>>>>>>>>>>>>>>>>>>>>>>>>
;板筋设置【BLSZ】
(defun C:bjsz()
;缺省设置
(if (null mjzj)(setq mjzj 8))
(if (null mjjj)(setq mjjj 200))
(if (null djzj)(setq djzj 8))
(if (null djjj)(setq djjj 200))
(if (null gjdj)(setq gjdj "HRB400"))
;更改输入
(setq sh(getint (strcat"\n输入钢筋等级 [1]HRB400 [2]CRB550 [3]CRB600H 空格[" gjdj "]:")))
(cond
((= sh 1)(setq gjdj "HRB400"))
((= sh 2)(setq gjdj "CRB550"))
((= sh 3)(setq gjdj "CRB600H"))
)
(setq sh(getint (strcat "\n输入通长面筋直径[" (rtos mjzj 2 0) "]:")))
(if (null sh)()(setq mjzj sh))
(setq sh(getint (strcat "输入通长面筋间距[" (rtos mjjj 2 0) "]:")))
(if (null sh)()(setq mjjj sh))
(setq sh(getint (strcat "\n输入通长底筋直径[" (rtos djzj 2 0) "]:")))
(if (null sh)()(setq djzj sh))
(setq sh(getint (strcat "输入通长底筋间距[" (rtos djjj 2 0) "]:")))
(if (null sh)()(setq djjj sh))
;面积计算
(cond
((= gjdj "HRB400")(setq gjqu 300))
((= gjdj "CRB550")(setq gjqu 400))
((= gjdj "CRB600H")(setq gjqu 430))
)
(setq dgmj(* 0.25 pi mjzj mjzj 1000))(setq mjmj(/ dgmj mjjj))
(setq dgmj(* 0.25 pi djzj djzj 1000))(setq djmj(/ dgmj djjj)) 
(princ (strcat "\n当前设置钢筋等级为:" gjdj "[" (rtos gjqu 2 0) "];"))
(princ (strcat "通长面筋" (rtos mjzj 2 0) "@" (rtos mjjj 2 0) "[" (rtos mjmj 2 0) "];"))
(princ (strcat "通长底筋" (rtos djzj 2 0) "@" (rtos djjj 2 0) "[" (rtos djmj 2 0) "]"))
(princ)
)
;板筋过滤【BJGL】
(defun C:bjgl()
(setvar "DIMSCALE" 1)
(setvar "cmdecho" 0)
(setq cl(getvar "clayer"))
(setq os (getvar "osmode"))
(setvar "osmode" 0)
(setq cec (getvar "Cecolor"))
(setvar "cecolor" "34")  
;检查是否有过滤参数
(if (null mjmj)
(C:bjsz)
(progn 
(princ (strcat "\n当前设置钢筋等级为:" gjdj "[" (rtos gjqu 2 0) "];"))
(princ (strcat "通长面筋" (rtos mjzj 2 0) "@" (rtos mjjj 2 0) "[" (rtos mjmj 2 0) "];"))
(princ (strcat "通长底筋" (rtos djzj 2 0) "@" (rtos djjj 2 0) "[" (rtos djmj 2 0) "]"))
)
);end_if
(princ "\n选择需要过滤的板筋计算书")
(setq ss (ssget '((0 . "TEXT"))))
;底筋过滤
(command "_.select" ss "")
(setq sss(ssget "p" '((8 . "12"))))
(if (null sss)()(progn
(setq len(sslength sss))
(setq i 0)
(repeat len 
(setq es(ssname sss i))
(setq el(entget es))
(setq str(cdr(assoc 1 el)))
(setq jsmj(atof str))
(if (< jsmj djmj)
(entmod (subst (cons 62 8)(assoc 62 el) el))
)
(setq i (+ i 1))
);end repeat
));end if

;面筋附加筋计算
(cond
((= gjdj "HRB400")
(progn
  (setq zj (list 6 8 6 10 8 10 12 14 16))
  (setq JJ (list 2 2 1  2 1  1  1  1  1))
  (setq gj (list "HRB400" "HRB400" "HRB400"  "HRB400" "HRB400"  "HRB400"  "HRB400"  "HRB400"  "HRB400"))

)
)
((= gjdj "CRB550")
(progn
  (setq zj (list 7 9 7 11 9 11 14 16))
  (setq JJ (list 2 2 1  2 1  1  1  1))
  (setq gj (list "CRB550" "CRB550" "CRB550"  "CRB550" "CRB550" "CRB550" "HRB400"  "HRB400"))

)
)
((= gjdj "CRB600H")
(progn
  (setq zj (list 7 9 7 11 9 11 14 16))
  (setq JJ (list 2 2 1  2 1  1  1  1))
  (setq gj (list "CRB600H" "CRB600H" "CRB600H" "CRB600H" "CRB600H" "CRB600H"  "HRB400"  "HRB400"))

)
)
);end cond
  (cond((= gjdj "HRB400")(setq tjqd 300))((= gjdj "CRB550")(setq tjqd 400))((= gjdj "CRB600H")(setq tjqd 430)))
  (setq len_ZJ (length zj))
  (setq i 0)
  (setq mj '())
  (setq wb '())
  (repeat len_ZJ
    (setq dgmj(* 0.25 pi (nth i zj) (nth i zj) 1000))
    (setq m(/ dgmj mjjj))
    (setq m(/ m (nth i JJ)))
    (cond((= (nth i gj) "HRB400")(setq qd 300))((= (nth i gj) "CRB550")(setq qd 400))((= (nth i gj) "CRB600H")(setq qd 430)))
    (setq m(* m qd))(setq m(/ m tjqd))
    (setq m(+ m mjmj))
    (setq mj(append mj (list m)))
    (cond((= (nth i gj) "HRB400")(setq fh "%%132"))((= (nth i gj) "CRB550")(setq fh "%%130%%140R%%141"))((= (nth i gj) "CRB600H")(setq fh "%%130%%140RH%%141")))
    (setq wb0(strcat  fh (itoa(nth i ZJ)) "@" (itoa (* mjjj (nth i JJ)))))
    (setq wb(append wb (list wb0)))
    (setq i (+ i 1))
  )
;面筋过滤
(setq chklay(tblsearch "layer" "QN-GS-配箍校核"))
(if chklay
()
(command  "-layer" "N" 	 "QN-GS-配箍校核" "C" "34" "QN-GS-配箍校核" "L" "Continuous"   "QN-GS-配箍校核" "p" "N"  "QN-GS-配箍校核" "")
)
(command "-layer" "S" "QN-GS-配箍校核" "")
(setq chklay(tblsearch "style" "QN_平面文字"))
(if (null chklay)
  (command "style" "QN_平面文字" "tssdeng.shx,hztxt.shx" "" "0.7" "" "" "" "")
)

(command "_.select" ss "")
(setq sss(ssget "p" '((8 . "13"))))
(if (null sss)()(progn
(setq num (list (cons 0 0) (cons 1 0) (cons 2 0) (cons 3 0) (cons 4 0) (cons 5 0) (cons 6 0) (cons 7 0) (cons 8 0) (cons 9 0)))
(setq num_cj 0)
(setq len(sslength sss))
(setq i 0)
(repeat len 
(setq es(ssname sss i))
(setq el(entget es))
(setq str(cdr(assoc 1 el)))
(setq jsmj(atoi str))
(setq point(cdr(assoc 10 el)))
(setq ang(cdr(assoc 50 el)))
(setq ang1(*(/ ang pi )180))
(setq ang1(+ ang1 90))
(setq dq(cdr(assoc 73 el)))
(setq kk 0)  
(if(> jsmj mjmj)(progn
		  
(if (>= ang1 360)(setq ang3(- ang1 360))(if(< ang1 0)(setq ang3(+ ang1 360))(setq ang3 ang1)))
(if (and(>= ang3 45 )(< ang3 87 ))
  (progn
    (setq as (abs(- ang3 90)))
    (setq jsmj(+ mjmj  (/ (- jsmj mjmj) (cos (/(* as pi)180)))))
    (setq ang 0)(setq kk 1)
 )
)
(if (and(>= ang3 93 )(< ang3 135 ))
  (progn
    (setq as (abs(- ang3 90)))
    (setq jsmj(+ mjmj  (/ (- jsmj mjmj) (cos (/(* as pi)180)))))
    (setq ang 0)(setq kk 1)
 )
)
(if (and(>=  ang3 225)(< ang3 267))
  (progn
    (setq as (abs(- ang3 270)))
    (setq jsmj(+ mjmj  (/ (- jsmj mjmj) (cos (/(* as pi)180)))))
    (setq ang 0)(setq kk 1)
 )
)
(if (and(>=  ang3 273)(< ang3 335))
  (progn
    (setq as (abs(- ang3 270)))
    (setq jsmj(+ mjmj  (/ (- jsmj mjmj) (cos (/(* as pi)180)))))
    (setq ang 0)(setq kk 1)
 )
)
(if (and(>= ang3 3 )(< ang3 45 ))
  (progn
    (setq as (abs(- ang3 0)))
    (setq jsmj(+ mjmj  (/ (- jsmj mjmj) (cos (/(* as pi)180)))))
    (setq ang (* 0.5 pi))(setq kk 1)(if (= dq 1)(setq dq 3)(setq dq 1))
 )
)
(if (and(>= ang3 335 )(< ang3 357 ))
  (progn
    (setq as (abs(- ang3 360)))
    (setq jsmj(+ mjmj  (/ (- jsmj mjmj) (cos (/(* as pi)180)))))
    (setq ang (* 0.5 pi))(setq kk 1)
 )
)
(if (and(>= ang3 135 )(< ang3 177 ))
  (progn
    (setq as (abs(- ang3 180)))
    (setq jsmj(+ mjmj  (/ (- jsmj mjmj) (cos (/(* as pi)180)))))
    (setq ang (* 0.5 pi))(setq kk 1)
 )
)
(if (and(>= ang3 183 )(< ang3 225 ))
  (progn
    (setq as (abs(- ang3 180)))
    (setq jsmj(+ mjmj  (/ (- jsmj mjmj) (cos (/(* as pi)180)))))
    (setq ang (* 0.5 pi))(setq kk 1)
 )
)
))
(setq ang1(*(/ ang pi )180))
(setq ang1(+ ang1 90))  
(setq pp (polar point ang 300))
(if (>= ang1 180)(setq ang1 (- ang1 180)))
(if (= 1 dq)(setq pp(polar pp (+ ang (* 0.5 pi)) 250)))
(setq j -1)(setq k 0)
(setq mj2 (append (list mjmj) mj))
(setq len_mj(length mj2))
(while (and(< j len_mj)(= k 0))
  (setq j (+ j 1))
  (if (>= (nth j mj2) jsmj)(setq k 1))
)
(if(= k 1)(setq num(subst(cons j (+ 1 (cdr(assoc j num))))(assoc j num) num))(setq num_cj(+ num_cj 1)))
(setq YS(list 8 3 4 5 140 145  202 220 225 6 7))
(if(= k 1)(entmod(subst(cons 62 (nth j YS))(assoc 62 el)el))(entmod(subst(cons 62 1)(assoc 62 el)el)))
(if (and(> j 0)(= k 1))(command "text" "s" "QN_平面文字" "j" "MC"  pp 100 ang1 (nth (- j 1) wb)))
(if (= k 0)(command "text" "s" "QN_平面文字" "j" "MC" pp 100 ang1 "超筋"))
(if (= kk 1)(command "text" "s" "QN_平面文字" "j" "MC"  (polar pp (/(*(- ang1 90) pi)180) 150) 100 ang1 (rtos jsmj 2 0)))

;(cond
;((<= jsmj mjmj)(entmod (subst (cons 62 8)(assoc 62 el) el)))
;((and(< =jsmj m1)(> jsmj mjmj))(progn(entmod (subst (cons 62 3)(assoc 62 el) el))(command "text" "s" "QN_平面文字" pp 100 ang1 t1)))
;((and(< =jsmj m2)(> jsmj m1))(progn(entmod (subst (cons 62 4)(assoc 62 el) el))(command "text" "s" "QN_平面文字" pp 100 ang1 t2)))
;((and(< =jsmj m3)(> jsmj m2))(progn(entmod (subst (cons 62 5)(assoc 62 el) el))(command "text" "s" "QN_平面文字" pp 100 ang1 t3)))
;((and(< =jsmj m4)(> jsmj m3))(progn(entmod (subst (cons 62 6)(assoc 62 el) el))(command "text" "s" "QN_平面文字" pp 100 ang1 t4)))
;((and(< =jsmj m5)(> jsmj m4))(progn(entmod (subst (cons 62 7)(assoc 62 el) el))(command "text" "s" "QN_平面文字" pp 100 ang1 t5)))
;(t(progn(entmod (subst (cons 62 1)(assoc 62 el) el))(command "text" "s" "" pp 100 0 "超筋")))
;)
(setq i (+ i 1))
);end repeat
(setq p1(list 0 0 0))
(command "text" "s" "" "j" "BL" p1 400 0 "面筋过滤结果统计：" "")
(setq es(entlast))
(setq el(entget es))
(setq s0(ssadd es))
(entmod (subst (cons 62 1)(assoc 62 el) el))
(setq p1(polar p1 (* -0.5 pi) 500))
(cond((= gjdj "HRB400")(setq fh "%%132"))((= gjdj "CRB550")(setq fh "%%130%%140R%%141"))((= gjdj "CRB600H")(setq fh "%%130%%140RH%%141")))
(setq wz(strcat "配筋:" fh  (rtos mjzj 2 0) "@" (rtos mjjj 2 0) "[" (rtos mjmj 2 0) "],颜色[8],数量[" (rtos (cdr(assoc 0 num)) 2 0)"];"))
(command "text" "s" "" "j" "BL" p1 400 0 wz)
(setq es(entlast))
(setq el(entget es))
(setq s0(ssadd es s0))
(entmod (subst (cons 62 8)(assoc 62 el) el))
(setq len_zj (length zj))
(setq n 0)
(repeat len_zj
  (setq p1(polar p1 (* -0.5 pi) 500))
  (setq wz(strcat "配筋:" fh  (rtos mjzj 2 0) "@" (rtos mjjj 2 0) "+" (nth n wb) "[" (rtos (nth n mj) 2 0) "],颜色[" (rtos (nth (+ n 1) YS) 2 0) "],数量[" (rtos (cdr(assoc (+ n 1) num)) 2 0)"];"))
  (command "text" "s" "" "j" "BL" p1 400 0 wz)
  (setq es(entlast))
  (setq el(entget es))
  (setq s0(ssadd es s0))
  (entmod (subst (cons 62 (nth (+ n 1) YS))(assoc 62 el) el))
  (setq n(+ n 1))
)
(setq p1(polar p1 (* -0.5 pi) 500))
(setq wz(strcat "超筋： [大于" (rtos (nth (- n 1) mj) 2 0) "],颜色[1],数量[" (rtos num_cj 2 0)"]。"))
(command "text" "s" "" "j" "BL" p1 400 0 wz)
(setq es(entlast))
(setq el(entget es))
(setq s0(ssadd es s0))
(entmod (subst (cons 62 1)(assoc 62 el) el))
));end if
(setvar "clayer" cl)
(setvar "osmode" os)
(setvar "cecolor" cec)   
(command "move" s0 "" (list 0 0 0))
(princ)
);end bjgl

;
;板筋改正【BJGZ】
(defun C:bjgz()
  (setq cl(getvar "clayer"))
  
  (setq os (getvar "osmode"))
  (setvar "osmode" 0)
  (setq cec (getvar "Cecolor"))
  (setvar "cecolor" "bylayer")
  (setq chklay(tblsearch "style" "QN_平面文字"))
  (if (null chklay)
    (command "style" "QN_平面文字" "tssdeng.shx,hztxt.shx" "" "0.7" "" "" "" "")
  )
  (setq sss(ssget  '((8 . "S-SLAB-FBAR")(0 . "LWPOLYLINE"))))
  (if (null sss)()
    (progn
      (setq len_sss(sslength sss))
      (setq i 0)
      (repeat len_sss
	(setq es1(ssname sss i))
	(setq zb(HH:PtLists es1));(princ "zb")(princ zb)
	(setq len_zb(length zb))
	(if(= len_zb 4)(progn
	  (setq lz(distance (nth 1 zb)(nth 2 zb)));(princ "lz")(princ lz)
	  (setq ang(angle (nth 1 zb)(nth 2 zb)))
	  (setq ang0(angle (nth 1 zb)(nth 0 zb)))
	  (setq ang1(* ang 180 (/ 1 pi)))(princ "ang1:")(princ ang1)	  
          ;;;;处理角度为1~45度板筋
	  (if (and(> ang1 1)(<= ang1 45))(progn
	    (setq pt1(polar (nth 1 zb) (+ pi ang) 300))
	    (setq pt2(polar pt1 ang0 600))
	    (setq pt4(polar (nth 2 zb) ang 300))
	    (setq pt3(polar pt4 ang0 600))
	    (setq sw1(ssget "wp" (list pt1 pt2 pt3 pt4) '((0 . "text")(8 . "S-SLAB-TEXT"))));(command "line" pt1 pt2 pt3 pt4 "")
	    (if(null sw1)(setq l1 0 l2 0)(progn
	    (command "JUSTIFYTEXT" sw1 "" "TC" )				   
	    (setq num_sw1(sslength sw1))
	      (if (= num_sw1 2)(progn
	      (setq w1es(ssname sw1 0))
	      (setq w1el(entget w1es))
	      (setq w1str(cdr(assoc 1 w1el)))
	      (setq w2es(ssname sw1 1))
	      (setq w2el(entget w2es))
	      (setq w2str(cdr(assoc 1 w2el)))
	      (setq zb_1(cdr(assoc 11 w1el)))
	      (setq zb_1x(car zb_1))

	      (setq zb_2(cdr(assoc 11 w2el)))
	      (setq zb_2x(car zb_2))
	      (if (< zb_1x zb_2x)(setq l1 (atoi w1str) l2 (atoi w2str))(setq l1 (atoi w2str) l2 (atoi w1str)))
	      ))
	      (if (= num_sw1 1)(progn
	      (setq w1es(ssname sw1 0))
	      (setq w1el(entget w1es))
	      (setq w1str(cdr(assoc 1 w1el)))
	      (setq zb_1(cdr(assoc 11 w1el)))
	      (setq zb_d1(distance zb_1 (nth 1 zb)))
	      (setq zb_d2(distance zb_1 (nth 2 zb)))
	      (if (< zb_d1 zb_d2)(setq l1 (atoi w1str) l2 0)(setq l1 0 l2 (atoi w1str)))
	      ))
	      (if (> num_sw1 2)(setq l1 0 l2 0))
	    ))
	    (setq pt1(polar (nth 1 zb) (+ pi ang) 800))
	    (setq pt2(polar (nth 2 zb) ang 800))
	    (setq pt3(polar pt2 (- ang0 pi) 600))
	    (setq pt4(polar pt1 (- ang0 pi) 600))
	    (setq sw3(ssget "wp" (list pt1 pt2 pt3 pt4) '((0 . "text")(8 . "S-SLAB-TTEX"))));(command "line" pt1 pt2 pt3 pt4 "")
	    (if (null sw3)()(progn
	    (setq w3es(ssname sw3 0))
	    (setq w3el(entget w3es))
	    (setq pjwz(cdr(assoc 1 w3el)))
	    ))
	    ;(princ "pjwz:")(princ pjwz)
	    ;处理中支座配筋
            (if (and (/= 0 l1) (/= 0 l2))
	      (progn
		(setq bk(- lz l1 l2));(princ "bk:")(princ bk)
		(setq cosang(cos ang))
		(setq bk_new(/ bk cosang))
		(setq l1_new(- (/ (+ l1 (* 0.5 bk)) cosang ) (* 0.5 bk_new)))
		(setq xx (/ l1_new 50))(setq xx(read (rtos (+ xx 0.5) 2 0)))(setq l1_new(* xx 50));(princ "l1_new:")(princ l1_new)
		(setq l2_new(- (/ (+ l2 (* 0.5 bk)) cosang) (* 0.5 bk_new)))
		(setq xx (/ l2_new 50))(setq xx(read (rtos (+ xx 0.5) 2 0)))(setq l2_new(* xx 50));(princ "l2_new:")(princ l2_new)
	        (setq ptz(list (* 0.5(+ (car(nth 1 zb)) (car(nth 2 zb)))) (* 0.5(+ (cadr(nth 1 zb)) (cadr(nth 2 zb)))) 0))
		(setq zb_new2(polar ptz pi (+ (* 0.5 bk_new)l1_new)))
		(setq zb_new1(polar zb_new2 (* 1.5 pi) 150))
		(setq zb_new3(polar ptz 0 (+ (* 0.5 bk_new)l2_new)))
		(setq zb_new4(polar zb_new3 (* 1.5 pi) 150))
		(setvar "clayer" "S-SLAB-FBAR")
	        (Make-LWPOLYLINE (list zb_new1 zb_new2 zb_new3 zb_new4))
		(command "erase" es1 "")
		(setq pt1(polar ptz pi (* 0.5 (+ bk_new l1_new))))
		(setq pt1(polar pt1 (* 1.5 pi) 90))
		(setvar "clayer" "S-SLAB-TEXT")
		(command "text" "S" "QN_平面文字" "j" "TC" pt1 250 0 l1_new)
		(command "erase" w1es "") 
		(setq pt2(polar ptz 0 (* 0.5 (+ bk_new l2_new))))
		(setq pt2(polar pt2 (* 1.5 pi) 90))
		(setvar "clayer" "S-SLAB-TEXT")
		(command "text" "S" "QN_平面文字" "j" "TC" pt2 250 0 l2_new)
		(command "erase" w2es "")
		(if (null sw3)()(progn
				  (setq pt3(polar ptz 0 (+ 60(* 0.5 bk_new))))
				  (setq pt3(polar pt3 (* 0.5 pi) 90))
				  (setvar "clayer" "S-SLAB-TTEX")
				  (command "text" "S" "QN_平面文字" "j" "BL" pt3 250 0 pjwz)
				  (command "erase" w3es "")
				  )
		)
	      );end_progn
            );end_(if (and (/= 0 l1) (/= 0 l2))
	    ;处理右端为边支座配筋,梁宽限定在600以下
	    (if (and(and (/= 0 l1) (= 0 l2))(<  (- lz l1 l2) 600))
	      (progn
		(setq zk(- lz l1));(princ "bk:")(princ bk)
		(setq cosang(cos ang))
		(setq zk_new(/ zk cosang))
		(setq l1_new(- (/ lz cosang ) zk_new))
		(setq xx (/ l1_new 50))(setq xx(read (rtos (+ xx 0.5) 2 0)))(setq l1_new(* xx 50));(princ "l1_new:")(princ l1_new)
		(setq ptz(nth 2 zb))
		(setq zb_new2(polar ptz pi (+ zk_new l1_new)))
		(setq zb_new1(polar zb_new2 (* 1.5 pi) 150))
		(setq zb_new3 ptz)
		(setq zb_new4(polar zb_new3 (* 1.5 pi) 150))
		(setvar "clayer" "S-SLAB-FBAR")
	        (Make-LWPOLYLINE (list zb_new1 zb_new2 zb_new3 zb_new4))
		(command "erase" es1 "")
		(setq pt1(polar ptz pi (+ zk_new(* 0.5 l1_new))))
		(setq pt1(polar pt1 (* 1.5 pi) 90))
		(setvar "clayer" "S-SLAB-TEXT")
		(command "text" "S" "QN_平面文字" "j" "TC" pt1 250 0 l1_new)
		(command "erase" w1es "") 
		(if (null sw3)()(progn
				  (setq pt3(polar ptz pi (+ 60 zk_new)))
				  (setq pt3(polar pt3 (* 0.5 pi) 90))
				  (setvar "clayer" "S-SLAB-TTEX")
				  (command "text" "S" "QN_平面文字" "j" "BR" pt3 250 0 pjwz)
				  (command "erase" w3es "")
				  )
		)
	      );end_progn
            );end_(if (and(and (/= 0 l1) (= 0 l2))(<  (- lz l1 l2) 600))
	     ;处理左端为边支座配筋,梁宽限定在600以下
	    (if (and(and (= 0 l1) (/= 0 l2))(<  (- lz l1 l2) 600))
	      (progn
		(setq zk(- lz l2));(princ "bk:")(princ bk)
		(setq cosang(cos ang))
		(setq zk_new(/ zk cosang))
		(setq l2_new(- (/ lz cosang ) zk_new))
		(setq xx (/ l2_new 50))(setq xx(read (rtos (+ xx 0.5) 2 0)))(setq l2_new(* xx 50));(princ "l1_new:")(princ l1_new)
		(setq ptz(nth 1 zb))
		(setq zb_new2 ptz)
		(setq zb_new1(polar zb_new2 (* 1.5 pi) 150))
		(setq zb_new3(polar ptz 0 (+ zk_new l1_new)))
		(setq zb_new4(polar zb_new3 (* 1.5 pi) 150))
		(setvar "clayer" "S-SLAB-FBAR")
	        (Make-LWPOLYLINE (list zb_new1 zb_new2 zb_new3 zb_new4))
		(command "erase" es1 "")
		(setq pt1(polar ptz 0 (+ zk_new(* 0.5 l1_new))))
		(setq pt1(polar pt1 (* 1.5 pi) 90))
		(setvar "clayer" "S-SLAB-TEXT")
		(command "text" "S" "QN_平面文字" "j" "TC" pt1 250 0 l1_new)
		(command "erase" w1es "") 
		(if (null sw3)()(progn
				  (setq pt3(polar ptz 0 (+ 60 zk_new)))
				  (setq pt3(polar pt3 (* 0.5 pi) 90))
				  (setvar "clayer" "S-SLAB-TTEX")
				  (command "text" "S" "QN_平面文字" "j" "BL" pt3 250 0 pjwz)
				  (command "erase" w3es "")
				  )
		)
	      );end_progn
            );end_(if (and(and (= 0 l1) (/= 0 l2))(<  (- lz l1 l2) 600))
	    
	  ));end_if(and(> ang1 1)(<= ang1 45))



          ;;;处理角度为315~359度板筋
	  (if (and(>= ang1 315)(< ang1 359))(progn
	    (setq pt1(polar (nth 1 zb) (- ang pi) 300))
	    (setq pt2(polar pt1 ang0 600))
	    (setq pt4(polar (nth 2 zb) ang 300))
	    (setq pt3(polar pt4 ang0 600))
	    (setq sw1(ssget "wp" (list pt1 pt2 pt3 pt4) '((0 . "text")(8 . "S-SLAB-TEXT"))));(command "line" pt1 pt2 pt3 pt4 "")
	    (if(null sw1)(setq l1 0 l2 0)(progn
	    (command "JUSTIFYTEXT" sw1 "" "TC" )
	    (setq num_sw1(sslength sw1))
	      (if (= num_sw1 2)(progn
	      (setq w1es(ssname sw1 0))
	      (setq w1el(entget w1es))
	      (setq w1str(cdr(assoc 1 w1el)))
	      (setq w2es(ssname sw1 1))
	      (setq w2el(entget w2es))
	      (setq w2str(cdr(assoc 1 w2el)))
	      (setq zb_1(cdr(assoc 11 w1el)))
	      (setq zb_1x(car zb_1))
	      (setq zb_2(cdr(assoc 11 w2el)))
	      (setq zb_2x(car zb_2))
	      (if (< zb_1x zb_2x)(setq l1 (atoi w1str) l2 (atoi w2str))(setq l1 (atoi w2str) l2 (atoi w1str)))
	      ))
	      (if (= num_sw1 1)(progn
	      (setq w1es(ssname sw1 0))
	      (setq w1el(entget w1es))
	      (setq w1str(cdr(assoc 1 w1el)))
	      (setq zb_1(cdr(assoc 11 w1el)))
	      (setq zb_d1(distance zb_1 (nth 1 zb)))
	      (setq zb_d2(distance zb_1 (nth 2 zb)))
	      (if (< zb_d1 zb_d2)(setq l1 (atoi w1str) l2 0)(setq l1 0 l2 (atoi w1str)))
	      ))
	      (if (> num_sw1 2)(setq l1 0 l2 0))
	    ))
	    (setq pt1(polar (nth 1 zb) (- ang pi) 800))
	    (setq pt2(polar (nth 2 zb) ang 800))
	    (setq pt3(polar pt2 (- ang0 pi) 600))
	    (setq pt4(polar pt1 (- ang0 pi) 600))
	    (setq sw3(ssget "wp" (list pt1 pt2 pt3 pt4) '((0 . "text")(8 . "S-SLAB-TTEX"))));(command "line" pt1 pt2 pt3 pt4 "")
	    (if (null sw3)()(progn
	    (setq w3es(ssname sw3 0))
	    (setq w3el(entget w3es))
	    (setq pjwz(cdr(assoc 1 w3el)))
	    ))
	    ;(princ "pjwz:")(princ pjwz)
	    ;处理中支座配筋
            (if (and (/= 0 l1) (/= 0 l2))
	      (progn
		(setq bk(- lz l1 l2));(princ "bk:")(princ bk)
		(setq cosang(cos (- (* 2 pi) ang)))
		(setq bk_new(/ bk cosang))
		(setq l1_new(- (/ (+ l1 (* 0.5 bk)) cosang ) (* 0.5 bk_new)))
		(setq xx (/ l1_new 50))(setq xx(read (rtos (+ xx 0.5) 2 0)))(setq l1_new(* xx 50));(princ "l1_new:")(princ l1_new)
		(setq l2_new(- (/ (+ l2 (* 0.5 bk)) cosang) (* 0.5 bk_new)))
		(setq xx (/ l2_new 50))(setq xx(read (rtos (+ xx 0.5) 2 0)))(setq l2_new(* xx 50));(princ "l2_new:")(princ l2_new)
	        (setq ptz(list (* 0.5(+ (car(nth 1 zb)) (car(nth 2 zb)))) (* 0.5(+ (cadr(nth 1 zb)) (cadr(nth 2 zb)))) 0))
		(setq zb_new2(polar ptz pi (+ (* 0.5 bk_new)l1_new)))
		(setq zb_new1(polar zb_new2 (* 1.5 pi) 150))
		(setq zb_new3(polar ptz 0 (+ (* 0.5 bk_new)l2_new)))
		(setq zb_new4(polar zb_new3 (* 1.5 pi) 150))
		(setvar "clayer" "S-SLAB-FBAR")
	        (Make-LWPOLYLINE (list zb_new1 zb_new2 zb_new3 zb_new4))
		(command "erase" es1 "")
		(setq pt1(polar ptz pi (* 0.5 (+ bk_new l1_new))))
		(setq pt1(polar pt1 (* 1.5 pi) 90))
		(setvar "clayer" "S-SLAB-TEXT")
		(command "text" "S" "QN_平面文字" "j" "TC" pt1 250 0 l1_new)
		(command "erase" w1es "") 
		(setq pt2(polar ptz 0 (* 0.5 (+ bk_new l2_new))))
		(setq pt2(polar pt2 (* 1.5 pi) 90))
		(setvar "clayer" "S-SLAB-TEXT")
		(command "text" "S" "QN_平面文字" "j" "TC" pt2 250 0 l2_new)
		(command "erase" w2es "")
		(if (null sw3)()(progn
                                  (setq pt3(polar ptz 0 (+ 60 (* 0.5 bk_new))))
				  (setq pt3(polar pt3 (* 0.5 pi) 90))
				  (setvar "clayer" "S-SLAB-TTEX")
				  (command "text" "S" "QN_平面文字" "j" "BL" pt3 250 0 pjwz)
				  (command "erase" w3es "")
				  )
		)
	      );end_progn
            );end_(if (and (/= 0 l1) (/= 0 l2))
	    ;处理右端为边支座配筋,梁宽限定在600以下
	    (if (and(and (/= 0 l1) (= 0 l2))(<  (- lz l1 l2) 600))
	      (progn
		(setq zk(- lz l1));(princ "bk:")(princ bk)
		(setq cosang(cos (- (* 2 pi) ang)))
		(setq zk_new(/ zk cosang))
		(setq l1_new(- (/ lz cosang ) zk_new))
		(setq xx (/ l1_new 50))(setq xx(read (rtos (+ xx 0.5) 2 0)))(setq l1_new(* xx 50));(princ "l1_new:")(princ l1_new)
		(setq ptz(nth 2 zb))
		(setq zb_new2(polar ptz pi (+ zk_new l1_new)))
		(setq zb_new1(polar zb_new2 (* 1.5 pi) 150))
		(setq zb_new3 ptz)
		(setq zb_new4(polar zb_new3 (* 1.5 pi) 150))
		(setvar "clayer" "S-SLAB-FBAR")
	        (Make-LWPOLYLINE (list zb_new1 zb_new2 zb_new3 zb_new4))
		(command "erase" es1 "")
		(setq pt1(polar ptz pi (+ zk_new(* 0.5 l1_new))))
		(setq pt1(polar pt1 (* 1.5 pi) 90))
		(setvar "clayer" "S-SLAB-TEXT")
		(command "text" "S" "QN_平面文字" "j" "TC" pt1 250 0 l1_new)
		(command "erase" w1es "") 
		(if (null sw3)()(progn
				  (setq pt3(polar ptz pi (+ 60 zk_new)))
				  (setq pt3(polar pt3 (* 0.5 pi) 90))
				  (setvar "clayer" "S-SLAB-TTEX")
				  (command "text" "S" "QN_平面文字" "j" "BR" pt3 250 0 pjwz)
				  (command "erase" w3es "")
				  )
		)
	      );end_progn
            );end_(if (and(and (/= 0 l1) (= 0 l2))(<  (- lz l1 l2) 600))
	     ;处理左端为边支座配筋,梁宽限定在600以下
	    (if (and(and (= 0 l1) (/= 0 l2))(<  (- lz l1 l2) 600))
	      (progn
		(setq zk(- lz l2));(princ "bk:")(princ bk)
		(setq cosang(cos (- (* 2 pi) ang)))
		(setq zk_new(/ zk cosang))
		(setq l2_new(- (/ lz cosang ) zk_new))
		(setq xx (/ l2_new 50))(setq xx(read (rtos (+ xx 0.5) 2 0)))(setq l2_new(* xx 50));(princ "l1_new:")(princ l1_new)
		(setq ptz(nth 1 zb))
		(setq zb_new2 ptz)
		(setq zb_new1(polar zb_new2 (* 1.5 pi) 150))
		(setq zb_new3(polar ptz 0 (+ zk_new l1_new)))
		(setq zb_new4(polar zb_new3 (* 1.5 pi) 150))
		(setvar "clayer" "S-SLAB-FBAR")
	        (Make-LWPOLYLINE (list zb_new1 zb_new2 zb_new3 zb_new4))
		(command "erase" es1 "")
		(setq pt1(polar ptz 0 (+ zk_new(* 0.5 l1_new))))
		(setq pt1(polar pt1 (* 1.5 pi) 90))
		(setvar "clayer" "S-SLAB-TEXT")
		(command "text" "S" "QN_平面文字" "j" "TC" pt1 250 0 l1_new)
		(command "erase" w1es "") 
		(if (null sw3)()(progn
				  (setq pt3(polar ptz 0 (+ 60 zk_new)))
				  (setq pt3(polar pt3 (* 0.5 pi) 90))
				  (setvar "clayer" "S-SLAB-TTEX")
				  (command "text" "S" "QN_平面文字" "j" "BL" pt3 250 0 pjwz)
				  (command "erase" w3es "")
				  )
		)
	      );end_progn
            );end_(if (and(and (= 0 l1) (/= 0 l2))(<  (- lz l1 l2) 600))
	  ));end_if(and(>=315 ang1 1)(< ang1 359))
	  
	  ;;;处理角度为45~89度板筋
	  (if (and(> ang1 45)(< ang1 89))(progn
	    (setq pt1(polar (nth 1 zb) (+ pi ang) 300))
	    (setq pt2(polar pt1 ang0 600))
	    (setq pt4(polar (nth 2 zb) ang 300))
	    (setq pt3(polar pt4 ang0 600))
	    (setq sw1(ssget "wp" (list pt1 pt2 pt3 pt4) '((0 . "text")(8 . "S-SLAB-TEXT"))));(command "line" pt1 pt2 pt3 pt4 "")
	    (if(null sw1)(setq l1 0 l2 0)(progn
	    (command "JUSTIFYTEXT" sw1 "" "TC" )
	    (setq num_sw1(sslength sw1))
	      (if (= num_sw1 2)(progn
	      (setq w1es(ssname sw1 0))
	      (setq w1el(entget w1es))
	      (setq w1str(cdr(assoc 1 w1el)))
	      (setq w2es(ssname sw1 1))
	      (setq w2el(entget w2es))
	      (setq w2str(cdr(assoc 1 w2el)))
	      (setq zb_1(cdr(assoc 11 w1el)))
	      (setq zb_1y(cadr zb_1))
	      (setq zb_2(cdr(assoc 11 w2el)))
	      (setq zb_2y(cadr zb_2))
	      (if (< zb_1y zb_2y)(setq l1 (atoi w1str) l2 (atoi w2str))(setq l1 (atoi w2str) l2 (atoi w1str)))
	      ))
	      (if (= num_sw1 1)(progn
	      (setq w1es(ssname sw1 0))
	      (setq w1el(entget w1es))
	      (setq w1str(cdr(assoc 1 w1el)))
	      (setq zb_1(cdr(assoc 11 w1el)))
	      (setq zb_d1(distance zb_1 (nth 1 zb)))
	      (setq zb_d2(distance zb_1 (nth 2 zb)))
	      (if (< zb_d1 zb_d2)(setq l1 (atoi w1str) l2 0)(setq l1 0 l2 (atoi w1str)))
	      ))
	      (if (> num_sw1 2)(setq l1 0 l2 0))
	    ))
	    (setq pt1(polar (nth 1 zb) (+ pi ang) 800))
	    (setq pt2(polar (nth 2 zb) ang 800))
	    (setq pt3(polar pt2 (- ang0 pi) 600))
	    (setq pt4(polar pt1 (- ang0 pi) 600))
	    (setq sw3(ssget "wp" (list pt1 pt2 pt3 pt4) '((0 . "text")(8 . "S-SLAB-TTEX"))));(command "line" pt1 pt2 pt3 pt4 "")
	    (if (null sw3)()(progn
	    (setq w3es(ssname sw3 0))
	    (setq w3el(entget w3es))
	    (setq pjwz(cdr(assoc 1 w3el)))
	    ))
	    ;(princ "pjwz:")(princ pjwz)
	    ;处理中支座配筋
            (if (and (/= 0 l1) (/= 0 l2))
	      (progn
		(setq bk(- lz l1 l2));(princ "bk:")(princ bk)
		(setq cosang(cos (- (* 0.5 pi) ang)))
		(setq bk_new(/ bk cosang))
		(setq l1_new(- (/ (+ l1 (* 0.5 bk)) cosang ) (* 0.5 bk_new)))
		(setq xx (/ l1_new 50))(setq xx(read (rtos (+ xx 0.5) 2 0)))(setq l1_new(* xx 50));(princ "l1_new:")(princ l1_new)
		(setq l2_new(- (/ (+ l2 (* 0.5 bk)) cosang) (* 0.5 bk_new)))
		(setq xx (/ l2_new 50))(setq xx(read (rtos (+ xx 0.5) 2 0)))(setq l2_new(* xx 50));(princ "l2_new:")(princ l2_new)
	        (setq ptz(list (* 0.5(+ (car(nth 1 zb)) (car(nth 2 zb)))) (* 0.5(+ (cadr(nth 1 zb)) (cadr(nth 2 zb)))) 0))
		(setq zb_new2(polar ptz (* 1.5 pi) (+ (* 0.5 bk_new)l1_new)))
		(setq zb_new1(polar zb_new2 0 150))
		(setq zb_new3(polar ptz (* 0.5 pi) (+ (* 0.5 bk_new)l2_new)))
		(setq zb_new4(polar zb_new3 0 150))
		(setvar "clayer" "S-SLAB-FBAR")
	        (Make-LWPOLYLINE (list zb_new1 zb_new2 zb_new3 zb_new4))
		(command "erase" es1 "")
		(setq pt1(polar ptz (* 1.5 pi) (* 0.5 (+ bk_new l1_new))))
		(setq pt1(polar pt1 0 90))
		(setvar "clayer" "S-SLAB-TEXT")
		(command "text" "S" "QN_平面文字" "j" "TC" pt1 250 90 l1_new)
		(command "erase" w1es "") 
		(setq pt2(polar ptz (* 0.5 pi) (* 0.5 (+ bk_new l2_new))))
		(setq pt2(polar pt2 0 90))
		(setvar "clayer" "S-SLAB-TEXT")
		(command "text" "S" "QN_平面文字" "j" "TC" pt2 250 90 l2_new)
		(command "erase" w2es "")
		(if (null sw3)()(progn
				  (setq pt3(polar ptz (* 0.5 pi) (+ 60 (* 0.5 bk_new))))
				  (setq pt3(polar pt3 pi 90))
				  (setvar "clayer" "S-SLAB-TTEX")
				  (command "text" "S" "QN_平面文字" "j" "BL" pt3 250 90 pjwz)
				  (command "erase" w3es "")
				  )
		)
	      );end_progn
            );end_(if (and (/= 0 l1) (/= 0 l2))
	    ;处理上端为边支座配筋,梁宽限定在600以下
	    (if (and(and (/= 0 l1) (= 0 l2))(<  (- lz l1 l2) 600))
	      (progn
		(setq zk(- lz l1));(princ "bk:")(princ bk)
		(setq cosang(cos (- (* 0.5 pi) ang)))
		(setq zk_new(/ zk cosang))
		(setq l1_new(- (/ lz cosang ) zk_new))
		(setq xx (/ l1_new 50))(setq xx(read (rtos (+ xx 0.5) 2 0)))(setq l1_new(* xx 50));(princ "l1_new:")(princ l1_new)
		(setq ptz(nth 2 zb))
		(setq zb_new2(polar ptz (* 1.5 pi) (+ zk_new l1_new)))
		(setq zb_new1(polar zb_new2 0 150))
		(setq zb_new3 ptz)
		(setq zb_new4(polar zb_new3 0 150))
		(setvar "clayer" "S-SLAB-FBAR")
	        (Make-LWPOLYLINE (list zb_new1 zb_new2 zb_new3 zb_new4))
		(command "erase" es1 "")
		(setq pt1(polar ptz (* 1.5 pi) (+ zk_new(* 0.5 l1_new))))
		(setq pt1(polar pt1 0 90))
		(setvar "clayer" "S-SLAB-TEXT")
		(command "text" "S" "QN_平面文字" "j" "TC" pt1 250 90 l1_new)
		(command "erase" w1es "") 
		(if (null sw3)()(progn
				  (setq pt3(polar ptz (* 1.5 pi) (+ 60 zk_new)))
				  (setq pt3(polar pt3 pi 90))
				  (setvar "clayer" "S-SLAB-TTEX")
				  (command "text" "S" "QN_平面文字" "j" "BR" pt3 250 90 pjwz)
				  (command "erase" w3es "")
				  )
		)
	      );end_progn
            );end_(if (and(and (/= 0 l1) (= 0 l2))(<  (- lz l1 l2) 600))
	     ;处理下端为边支座配筋,梁宽限定在600以下
	    (if (and(and (= 0 l1) (/= 0 l2))(<  (- lz l1 l2) 600))
	      (progn
		(setq zk(- lz l2));(princ "bk:")(princ bk)
		(setq cosang(cos (- (* 0.5 pi) ang)))
		(setq zk_new(/ zk cosang))
		(setq l2_new(- (/ lz cosang ) zk_new))
		(setq xx (/ l2_new 50))(setq xx(read (rtos (+ xx 0.5) 2 0)))(setq l2_new(* xx 50));(princ "l1_new:")(princ l1_new)
		(setq ptz(nth 1 zb))
		(setq zb_new2 ptz)
		(setq zb_new1(polar zb_new2 0 150))
		(setq zb_new3(polar ptz (* 0.5 pi) (+ zk_new l1_new)))
		(setq zb_new4(polar zb_new3 0 150))
		(setvar "clayer" "S-SLAB-FBAR")
	        (Make-LWPOLYLINE (list zb_new1 zb_new2 zb_new3 zb_new4))
		(command "erase" es1 "")
		(setq pt1(polar ptz (* 0.5 pi) (+ zk_new(* 0.5 l1_new))))
		(setq pt1(polar pt1 0 90))
		(setvar "clayer" "S-SLAB-TEXT")
		(command "text" "S" "QN_平面文字" "j" "TC" pt1 250 90 l1_new)
		(command "erase" w1es "") 
		(if (null sw3)()(progn
				  (setq pt3(polar ptz (* 0.5 pi) (+ 60 zk_new)))
				  (setq pt3(polar pt3 pi 90))
				  (setvar "clayer" "S-SLAB-TTEX")
				  (command "text" "S" "QN_平面文字" "j" "BL" pt3 250 90 pjwz)
				  (command "erase" w3es "")
				  )
		)
	      );end_progn
            );end_(if (and(and (= 0 l1) (/= 0 l2))(<  (- lz l1 l2) 600))
	  ));end_if(and(> ang1 45)(< ang1 89))
	    
	    ;;;处理角度为271~315度板筋
	  (if (and(> ang1 271)(< ang1 315))(progn
	    (setq pt1(polar (nth 1 zb) (- ang pi) 300))
	    (setq pt2(polar pt1 ang0 600))
	    (setq pt4(polar (nth 2 zb) ang 300))
	    (setq pt3(polar pt4 ang0 600))
	    (setq sw1(ssget "wp" (list pt1 pt2 pt3 pt4) '((0 . "text")(8 . "S-SLAB-TEXT"))));(command "line" pt1 pt2 pt3 pt4 "")
	    (if(null sw1)(setq l1 0 l2 0)(progn
	    (command "JUSTIFYTEXT" sw1 "" "TC" )
	    (setq num_sw1(sslength sw1))
	      (if (= num_sw1 2)(progn
	      (setq w1es(ssname sw1 0))
	      (setq w1el(entget w1es))
	      (setq w1str(cdr(assoc 1 w1el)))
	      (setq w2es(ssname sw1 1))
	      (setq w2el(entget w2es))
	      (setq w2str(cdr(assoc 1 w2el)))
	      (setq zb_1(cdr(assoc 11 w1el)))
	      (setq zb_1y(cadr zb_1))
	      (setq zb_2(cdr(assoc 11 w2el)))
	      (setq zb_2y(cadr zb_2))
	      (if (< zb_1y zb_2y)(setq l1 (atoi w1str) l2 (atoi w2str))(setq l1 (atoi w2str) l2 (atoi w1str)))
	      ))
	      (if (= num_sw1 1)(progn
	      (setq w1es(ssname sw1 0))
	      (setq w1el(entget w1es))
	      (setq w1str(cdr(assoc 1 w1el)))
	      (setq zb_1(cdr(assoc 11 w1el)))
	      (setq zb_d1(distance zb_1 (nth 1 zb)))
	      (setq zb_d2(distance zb_1 (nth 2 zb)))
	      (if (< zb_d1 zb_d2)(setq l1 (atoi w1str) l2 0)(setq l1 0 l2 (atoi w1str)))
	      ))
	      (if (> num_sw1 2)(setq l1 0 l2 0))
	    ))
	    (setq pt1(polar (nth 1 zb) (- ang pi) 800))
	    (setq pt2(polar (nth 2 zb) ang 800))
	    (setq pt3(polar pt2 (- ang0 pi) 600))
	    (setq pt4(polar pt1 (- ang0 pi) 600))
	    (setq sw3(ssget "wp" (list pt1 pt2 pt3 pt4) '((0 . "text")(8 . "S-SLAB-TTEX"))));(command "line" pt1 pt2 pt3 pt4 "")
	    (if (null sw3)()(progn
	    (setq w3es(ssname sw3 0))
	    (setq w3el(entget w3es))
	    (setq pjwz(cdr(assoc 1 w3el)))
	    ))
	    ;(princ "pjwz:")(princ pjwz)
	    ;处理中支座配筋
            (if (and (/= 0 l1) (/= 0 l2))
	      (progn
		(setq bk(- lz l1 l2));(princ "bk:")(princ bk)
		(setq cosang(cos (-  ang (* 1.5 pi))))
		(setq bk_new(/ bk cosang))
		(setq l1_new(- (/ (+ l1 (* 0.5 bk)) cosang ) (* 0.5 bk_new)))
		(setq xx (/ l1_new 50))(setq xx(read (rtos (+ xx 0.5) 2 0)))(setq l1_new(* xx 50));(princ "l1_new:")(princ l1_new)
		(setq l2_new(- (/ (+ l2 (* 0.5 bk)) cosang) (* 0.5 bk_new)))
		(setq xx (/ l2_new 50))(setq xx(read (rtos (+ xx 0.5) 2 0)))(setq l2_new(* xx 50));(princ "l2_new:")(princ l2_new)
	        (setq ptz(list (* 0.5(+ (car(nth 1 zb)) (car(nth 2 zb)))) (* 0.5(+ (cadr(nth 1 zb)) (cadr(nth 2 zb)))) 0))
		(setq zb_new2(polar ptz (* 1.5 pi) (+ (* 0.5 bk_new)l1_new)))
		(setq zb_new1(polar zb_new2 0 150))
		(setq zb_new3(polar ptz (* 0.5 pi) (+ (* 0.5 bk_new)l2_new)))
		(setq zb_new4(polar zb_new3 0 150))
		(setvar "clayer" "S-SLAB-FBAR")
	        (Make-LWPOLYLINE (list zb_new1 zb_new2 zb_new3 zb_new4))
		(command "erase" es1 "")
		(setq pt1(polar ptz (* 1.5 pi) (* 0.5 (+ bk_new l1_new))))
		(setq pt1(polar pt1 0 90))
		(setvar "clayer" "S-SLAB-TEXT")
		(command "text" "S" "QN_平面文字" "j" "TC" pt1 250 90 l1_new)
		(command "erase" w1es "") 
		(setq pt2(polar ptz (* 0.5 pi) (* 0.5 (+ bk_new l2_new))))
		(setq pt2(polar pt2 0 90))
		(setvar "clayer" "S-SLAB-TEXT")
		(command "text" "S" "QN_平面文字" "j" "TC" pt2 250 90 l2_new)
		(command "erase" w2es "")
		(if (null sw3)()(progn
				  (setq pt3(polar ptz (* 0.5 pi) (+ 60 (* 0.5 bk_new))))
				  (setq pt3(polar pt3 pi 90))
				  (setvar "clayer" "S-SLAB-TTEX")
				  (command "text" "S" "QN_平面文字" "j" "BL" pt3 250 90 pjwz)
				  (command "erase" w3es "")
				  )
		)
	      );end_progn
            );end_(if (and (/= 0 l1) (/= 0 l2))
	    ;处理上端为边支座配筋,梁宽限定在600以下
	    (if (and(and (/= 0 l1) (= 0 l2))(<  (- lz l1 l2) 600))
	      (progn
		(setq zk(- lz l1));(princ "bk:")(princ bk)
		(setq cosang(cos (-  ang (* 1.5 pi))))
		(setq zk_new(/ zk cosang))
		(setq l1_new(- (/ lz cosang ) zk_new))
		(setq xx (/ l1_new 50))(setq xx(read (rtos (+ xx 0.5) 2 0)))(setq l1_new(* xx 50));(princ "l1_new:")(princ l1_new)
		(setq ptz(nth 2 zb))
		(setq zb_new2(polar ptz (* 1.5 pi) (+ zk_new l1_new)))
		(setq zb_new1(polar zb_new2 0 150))
		(setq zb_new3 ptz)
		(setq zb_new4(polar zb_new3 0 150))
		(setvar "clayer" "S-SLAB-FBAR")
	        (Make-LWPOLYLINE (list zb_new1 zb_new2 zb_new3 zb_new4))
		(command "erase" es1 "")
		(setq pt1(polar ptz (* 1.5 pi) (+ zk_new(* 0.5 l1_new))))
		(setq pt1(polar pt1 0 90))
		(setvar "clayer" "S-SLAB-TEXT")
		(command "text" "S" "QN_平面文字" "j" "TC" pt1 250 90 l1_new)
		(command "erase" w1es "") 
		(if (null sw3)()(progn
				  (setq pt3(polar ptz (* 1.5 pi) (+ 60 zk_new)))
				  (setq pt3(polar pt3 pi 90))
				  (setvar "clayer" "S-SLAB-TTEX")
				  (command "text" "S" "QN_平面文字" "j" "BR" pt3 250 90 pjwz)
				  (command "erase" w3es "")
				  )
		)
	      );end_progn
            );end_(if (and(and (/= 0 l1) (= 0 l2))(<  (- lz l1 l2) 600))
	     ;处理下端为边支座配筋,梁宽限定在600以下
	    (if (and(and (= 0 l1) (/= 0 l2))(<  (- lz l1 l2) 600))
	      (progn
		(setq zk(- lz l2));(princ "bk:")(princ bk)
		(setq cosang(cos (-  ang (* 1.5 pi))))
		(setq zk_new(/ zk cosang))
		(setq l2_new(- (/ lz cosang ) zk_new))
		(setq xx (/ l2_new 50))(setq xx(read (rtos (+ xx 0.5) 2 0)))(setq l2_new(* xx 50));(princ "l1_new:")(princ l1_new)
		(setq ptz(nth 1 zb))
		(setq zb_new2 ptz)
		(setq zb_new1(polar zb_new2 0 150))
		(setq zb_new3(polar ptz (* 0.5 pi) (+ zk_new l1_new)))
		(setq zb_new4(polar zb_new3 0 150))
		(setvar "clayer" "S-SLAB-FBAR")
	        (Make-LWPOLYLINE (list zb_new1 zb_new2 zb_new3 zb_new4))
		(command "erase" es1 "")
		(setq pt1(polar ptz (* 0.5 pi) (+ zk_new(* 0.5 l1_new))))
		(setq pt1(polar pt1 0 90))
		(setvar "clayer" "S-SLAB-TEXT")
		(command "text" "S" "QN_平面文字" "j" "TC" pt1 250 90 l1_new)
		(command "erase" w1es "") 
		(if (null sw3)()(progn
				  (setq pt3(polar ptz (* 0.5 pi) (+ 60 zk_new)))
				  (setq pt3(polar pt3 pi 90))
				  (setvar "clayer" "S-SLAB-TTEX")
				  (command "text" "S" "QN_平面文字" "j" "BL" pt3 250 90 pjwz)
				  (command "erase" w3es "")
				  )
		)
	      );end_progn
            );end_(if (and(and (= 0 l1) (/= 0 l2))(<  (- lz l1 l2) 600))
	  ));end_if (and(> ang1 271)(< ang1 315))






	  
	));end_if(= len_zb 4)






	(setq i (+ i 1))
	);end_repeat
      );end_progn
    );end_if
  );end_defun
  ;(princ len_sss)



;;加载使用的多线段工具
;;164.3 [功能] 多段线端点列表 By 自贡黄明儒
;;示例(HH:PtLists (car (entsel)))
(defun HH:PtLists (en)
  (mapcar 'cdr
          (vl-remove-if-not '(lambda (x) (= (car x) 10)) (entget en))
  )
)
;;164.31 [功能] 点表生成多段线
(defun Make-LWPOLYLINE (lst / PT)
  (entmake (append (list '(0 . "LWPOLYLINE")
                         '(100 . "AcDbEntity")
                         '(100 . "AcDbPolyline")
			 '(43 . 30)
                         (cons 90 (length lst))
                   )
                   (mapcar '(lambda (pt) (cons 10 pt)) lst)
           )
  )
)

;加载显示
(princ "\n板筋工具命令：板筋设置【BLSZ】设置通长筋   板筋过滤【BJGL】过滤计算书    板筋改正【BJGZ】斜向面筋改正向")
(princ)
