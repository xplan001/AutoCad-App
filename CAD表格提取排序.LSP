(defun c:xxx()
  (setq lu (getpoint "\n please input the first corner point"))
  (setq rd (getpoint "\n please input the second corner point"))
  (setq fna (getstring "\ninput the file name:"))
  (setq fna (strcat fna ".txt"))
  (setq fna (strcat "C:/Users/Administrator/Desktop/" fna))
  (princ "\n找不到文件？？在桌面啊！有木有啊~~")
  (princ fna)
  (setq xlist nil ltext nil vlist nil)
  (setq a (ssget "c" lu rd))
  (setq num (sslength a))
  (setq i 0)
  (while (< i num)
    (setq ienta (entget (ssname a i)))
    (setq iflag (cdr (assoc 0 ienta)))
    (if (= iflag "MTEXT")
      (command "explode" (ssname a i))
      )
    (setq i (1+ i))
    )
  ;calculate the row of table.
  (setq a (ssget "c" lu rd '((0 . "TEXT"))))
  (setq num (sslength a))
  (setq k 0 n 1)
  (while (< k num)
    (setq kenta (entget (ssname a k)))
    (setq kxyz (cdr (assoc 10 kenta)))
    (setq kx (car kxyz))
    (setq kheight (cdr (assoc 40 kenta)))
    (setq kscale (cdr (assoc 41 kenta)))
    (setq ktext (cdr (assoc 1 kenta)))
    (setq ktlen (strlen ktext))
    (setq k0 (1+ k))
    (while (< k0 num)
      (setq k0enta (entget (ssname a k0)))
      (setq k0xyz (cdr (assoc 10 k0enta)))
      (setq k0x (car k0xyz))
      (if (> kx k0x)
	(progn
	  (setq kx k0x)
	  (setq kheight (cdr (assoc 40 k0enta)))
	  (setq kscale (cdr (assoc 41 k0enta)))
	  (setq ktext (cdr (assoc 1 k0enta)))
	  (setq ktlen (strlen ktext))
	  )
	(setq k0 (1+ k0))
	)
      )
    (setq ktlen (+ ktlen 1))
    (setq xvar (* kheight kscale ktlen))
    (setq xlist (cons kx xlist))
    (setq tlist (cons n tlist))
    (setq vlist (cons xvar vlist))
    (setq n (1+ n))
    (setq k1 (1+ k))
    (while (< k1 num)
      (setq k1enta (entget (ssname a k1)))
      (setq k1xyz (cdr (assoc 10 k1enta)))
      (setq k1text (cdr (assoc 1 k1enta)))
;缩小x值的变化范围.
      (setq k1tlen (strlen k1text))
      (setq k1scale (cdr (assoc 41 k1enta)))
      (setq k1height (cdr (assoc 40 k1enta)))
      (setq k1xvar (* k1tlen k1scale k1height))
      (setq xvar1 (- xvar k1xvar))
      (if (<= xvar1 0)
	(setq xvar1 kheight)
	)
;缩小x值的变化范围.
      (setq k1x (car k1xyz))
      (if (and (>= k1x kx) (< k1x (+ kx xvar1)))
	(progn
	  (ssdel (ssname a k1) a)
	  (setq num (sslength a))
	  (setq k1 0 k 0)
	  )
	(setq k1 (1+ k1))
	)
      )
    (setq k (1+ k))
    )
  ;(setq tlist (reverse tlist))
  ;(setq tlist1 tlist)
  (setq xlist (reverse xlist))
  (princ "\nxlist=")
  (princ xlist)
  (setq vlist (reverse vlist))
    (princ "\nvlist=")
  (princ vlist)
  (setq n (1- n))
;以上是计算所选表格列数.
;the follow program is output the text of table.
  (setq a (ssget "c" lu rd '((0 . "TEXT"))))
  (setq num (sslength a))
  (setq k 0  j 0 p 0)
  (setq fp (open fna "w"))
;while start.
  (while (< k num)
    (setq kenta (entget (ssname a k)))
    (setq selheight (cdr (assoc 40 kenta)))
    (setq selnum k)
    (setq selxyz (cdr (assoc 10 kenta)))
    (setq selx (car selxyz))
    (setq sely (nth 1 selxyz))
    (setq seltext (cdr (assoc 1 kenta)))
    (setq seltlen (strlen seltext))
    (setq selscale (cdr (assoc 41 kenta)))
    (setq selxvar (* selheight seltlen selscale))
    (setq kk (1+ k))
;while 1 start.
    (while (< kk num)
      (setq kkenta (entget (ssname a kk)))
      (setq kkxyz (cdr (assoc 10 kkenta)))
      (setq kkx (car kkxyz))
      (setq kky (nth 1 kkxyz))
      (setq kktext (cdr (assoc 1 kkenta)))
      (setq kktlen (strlen kktext))
      (setq kkscale (cdr (assoc 41 kkenta)))
      (if (< (abs (- sely kky)) (* selheight 0.5))
	(if (> selx kkx)
	  (progn
	    (setq selnum kk)
            (setq selx kkx)
            (setq sely kky)
            (setq seltext kktext)
	    (setq selheight (cdr (assoc 40 kkenta)))
	    (setq selxvar (* kktlen kkscale selheight))
            )
	  )
	(if (>= (- kky sely) (* selheight 0.5))
	  (progn
	    (setq selnum kk)
	    (setq selx kkx)
            (setq sely kky)
            (setq seltext kktext)
	    (setq selheight (cdr (assoc 40 kkenta)))
	    (setq selxvar (* kktlen kkscale selheight))
            )
	  )
	)
        (setq kk (1+ kk))
      )
;while 1 end.
    (if (= j 0)
      (progn
	(setq j (1+ j))                 
        (setq jy sely)
        )
      )
    (if (< (abs (- sely jy)) (* selheight 0.5))
      (progn
	(setq m 0)
	(while (< m n)
	  (setq xrow (nth m xlist))
	  (setq xvar (nth m vlist))
	  (setq xvar1 (- xvar selxvar))
          (if (<= xvar1 0)
	    (setq xvar1 selheight)
	    )
	  (if (and (>= selx xrow) (< selx (+ xrow xvar1)))
	    (setq g m)
	    )
	  (setq m (1+ m))
	  )
;the following, confirm the situation of seltext.
	(if (= p g)
	  (progn
	    (setq ltext (cons seltext ltext))
	    (setq p (1+ g))
	    )
	  (progn
	    (while (< p g)
	      (setq ltext (cons " " ltext))
	      (setq p (1+ p))
	      )
	    (setq ltext (cons seltext ltext))
	    (setq p (1+ g))
	    )
	  )
;above program, confirm the situation of seltext.
	)
	(progn
	  (setq p 0)
	  (setq m 0)
	  (setq ltext1 ltext)
	  (setq ltext1 (reverse ltext1))
	  (setq ltext nil)
	  (setq jy sely)
	  (while (< m n)
	    (setq xrow (nth m xlist))
	    (setq xvar (nth m vlist))
	    (setq xvar1 (- xvar selxvar))
            (if (<= xvar1 0)
	      (setq xvar1 selheight)
	      )
	    (if (and (>= selx xrow) (< selx (+ xrow xvar1)))
	      (setq g m)
	      )
	    (setq m (1+ m))
	    )
;the following, confirm the situation of seltext.
	(if (= p g)
	  (progn
	    (setq ltext (cons seltext ltext))
	    (setq p (1+ g))
	    )
	  (progn
	    (while (< p g)
	      (setq ltext (cons " " ltext))
	      (setq p (1+ p))
	      )
	    (setq ltext (cons seltext ltext))
	    (setq p (1+ g))
	    )
	  )
;above program, confirm the situation of seltext.
	  (foreach d ltext1 (progn (princ d fp) (princ "\t" fp)))
	  (princ "\n" fp)
	  )
	)
      (ssdel (ssname a selnum) a)
      (setq k 0)
      (setq num (sslength a))
      (if (= num 0)
	(progn
	  (setq ltext (reverse ltext))
	  (foreach d ltext (progn (princ d fp) (princ "\t" fp)))
	  )
	)
      )
    
;(princ "\nwhile dialogue is end")
;while end.
    (close fp)
    (princ)
  )
