(defun c:YL()
  (setvar "cmdecho" 0)
  (princ "设置约束边缘构件只适用于底部加强区及上一层        ")
  (princ "请输入抗震等级(默认值") (princ ek) (princ "级):")
  (setq ek0 (getint))
  (if (/= ek0 nil)
    (setq ek ek0)
    )
  (princ "请输入设防烈度(默认值") (princ ekm) (princ "度):")
  (setq ekm0 (getint))
  (if (/= ekm0 nil)
    (setq ekm ekm0)
    )
  (setq L0 400)
  (setq d_wall0 200)
  (setq s0 (ssget))
  (setq s_zyb (ssadd))
  (setq s0_long (sslength s0))
  (setq ct 0)
  (repeat s0_long
    (setq e (ssname s0 ct))
    (setq e_list (entget e))
    (if (and (= (cdr(assoc 0 e_list)) "TEXT") (= (cdr(assoc 8 e_list)) "20001"))
      (progn
	(ssadd e s_zyb)
        (ssdel e s0)
	)
      (setq ct (+ ct 1))
      )
    )
  (setq s_zyb_long (sslength s_zyb))
  (setq e (ssname s_zyb 0))
  (setq e_list (entget e))
  (setq zyb (distof(cdr(assoc 1 e_list))))
  (setq ct 1)
  (repeat (1- s_zyb_long)
    (setq e (ssname s_zyb ct))
    (setq e_list (entget e))
    (setq zyb1 (distof(cdr(assoc 1 e_list))))
    (if (> zyb1 zyb)
      (setq zyb zyb1)
      )
    (setq ct (+ ct 1))
    )
  (setq s_w s0)
  (setq s_w_long (sslength s_w))

  ;;;;下面设定Lck,以”一“字墙的为标准，非”一“字墙的减0.05
  (if (and (= ek 1) (= ekm 9))
    (progn
      (setq zyb0 (/ (float 2) 10))
      (if (<= zyb zyb0)
	(setq Lck (/ (float 2) 10))
	(setq Lck (/ (float 25) 100))
	)
      )
    )
  (if (and (= ek 1) (= ekm 8))
    (progn
      (setq zyb0 (/ (float 3) 10))
      (if (<= zyb zyb0)
	(setq Lck (/ (float 15) 100))
	(setq Lck (/ (float 20) 100))
	)
      )
    )
  (if (or (= ek 2) (= ek 3))
    (progn
      (setq zyb0 (/ (float 4) 10))
      (if (<= zyb zyb0)
	(setq Lck (/ (float 15) 100))
	(setq Lck (/ (float 20) 100))
	)
      )
    )
      
  ;;;;设定Lck结束,以”一“字墙的为标准，非”一“字墙的减0.05
  (if (and(= 3 ek) (<= zyb (/ (float 30) 100)))
    (princ"轴压比小于等于0.3的三级剪力墙请设置构造边缘构件")
    (progn
      (setq s_w s0)
      (setq s_w_long (sslength s_w))
      (setq e (ssname s_w 0))
      (setq e_list (entget e))
      (setq e_list_long (length e_list));从0开始
      (setq p1 (cdr(nth (- e_list_long 25) e_list)))
      (setq p2 (cdr(nth (- e_list_long 21) e_list)))
      (setq p3 (cdr(nth (- e_list_long 17) e_list)))
      (setq p4 (cdr(nth (- e_list_long 13) e_list)))
      (setq p5 (cdr(nth (- e_list_long 9) e_list)))
      (setq p6 (cdr(nth (- e_list_long 5) e_list)))
      (setq d12 (distance p1 p2))
      (setq d23 (distance p2 p3))
      (setq d34 (distance p3 p4))
      (setq d45 (distance p4 p5))
  (setq d56 (distance p5 p6))
  (setq d61 (distance p6 p1))
  (setq p1x (car p1))
  (setq p1y (cadr p1))
  (setq p2x (car p2))
  (setq p2y (cadr p2))
  (setq p3x (car p3))
  (setq p3y (cadr p3))
  (setq p4x (car p4))
  (setq p4y (cadr p4))
  (setq p5x (car p5))
  (setq p5y (cadr p5))
  (setq p6x (car p6))
  (setq p6y (cadr p6))
  (setq pdate (list p1 p2 p3 p4 p5 p6 p1 p2 p3 p4 p5 p6 p1 p2 p3 p4 p5 p6 p1 p2 p3 p4 p5 p6 p1 p2 p3 p4 p5 p6))
  (setq p_dist_date (list d12 d23 d34 d45 d56 d61 d12 d23 d34 d45 d56 d61 d12 d23 d34 d45 d56 d61 d12 d23 d34 d45 d56 d61 d12 d23 d34 d45 d56 d61))
  (setq p_dist_max (max d12 d23 d34 d45 d56 d61))
  (setq pp_dist_date0 (+ (nth 0 p_dist_date) (nth 1 p_dist_date)))
  (setq pp_dist_date1 (+ (nth 1 p_dist_date) (nth 2 p_dist_date)))
  (setq pp_dist_date2 (+ (nth 2 p_dist_date) (nth 3 p_dist_date)))
  (setq pp_dist_date3 (+ (nth 3 p_dist_date) (nth 4 p_dist_date)))
  (setq pp_dist_date4 (+ (nth 4 p_dist_date) (nth 5 p_dist_date)))
  (setq pp_dist_date5 (+ (nth 5 p_dist_date) (nth 0 p_dist_date)))
  (setq pp_dist_date_max (max pp_dist_date0  pp_dist_date1 pp_dist_date2 pp_dist_date3 pp_dist_date4 pp_dist_date5))
  (if (= pp_dist_date0 pp_dist_date_max)
    (setq m 1)
    )
  (if (= pp_dist_date1 pp_dist_date_max)
    (setq m 2)
    )
  (if (= pp_dist_date2 pp_dist_date_max)
    (setq m 3)
    )
  (if (= pp_dist_date3 pp_dist_date_max)
    (setq m 4)
    )
  (if (= pp_dist_date4 pp_dist_date_max)
    (setq m 5)
    )
  (if (= pp_dist_date5 pp_dist_date_max)
    (setq m 0)
    );;;m为L型角点
  (setq pp0 (nth m pdate))
  (setq pp1 (nth (+ m 1) pdate))
  (setq pp2 (nth (+ m 2) pdate))
  (setq pp3 (nth (+ m 3) pdate))
  (setq pp4 (nth (+ m 4) pdate))
  (setq pp5 (nth (+ m 5) pdate))
  (setq ppdate (list pp0 pp1 pp2 pp3 pp4 pp5 pp0));;;新点阵
  (setq pp_dist_date0 (nth m p_dist_date))
  (setq pp_dist_date1 (nth (+ m 1) p_dist_date))
  (setq pp_dist_date2 (nth (+ m 2) p_dist_date))
  (setq pp_dist_date3 (nth (+ m 3) p_dist_date))
  (setq pp_dist_date4 (nth (+ m 4) p_dist_date))
  (setq pp_dist_date5 (nth (+ m 5) p_dist_date))
  (setq pp_dist_date (list pp_dist_date0 pp_dist_date1 pp_dist_date2 pp_dist_date3 pp_dist_date4 pp_dist_date5));;;新变长阵
  (if (> pp_dist_date5 pp_dist_date0)
    (progn
      (setq ppdate (reverse ppdate))
      (setq pp_dist_date (reverse pp_dist_date))
      )
    );;;此判断保证以最长边作为起边！！！
  (setq L1_P1 (nth 1 ppdate))
  (setq L1_P2 (nth 2 ppdate))
  (setq L1_P0 (nth 3 ppdate))  ;;;;移动方向判定点
  (setq bw (nth 1 pp_dist_date))
  (setq bf (nth 4 pp_dist_date))
  (setq d_wall_long1 (nth 0 pp_dist_date))
  (setq d_wall_long2 (nth 2 pp_dist_date))
  (setq d_wall_long3 (nth 5 pp_dist_date))
  (if (> bf (* 4 d_wall_long3)) ;;;如果为真要按“一”字墙设计。Lck无需调整！
     (progn;;;;;;;;;;;;;;;;;;;;;;;;;;;;;;;;;progn1
       (setq Lc (* d_wall_long1 Lck))
       (setq Lc (float(* (fix(/ (+ LC 49) 50)) 50)))
	(setq L4_P1 (nth 0 ppdate))
	(setq L4_P2 (nth 5 ppdate))
	(setq L4_P0 (nth 4 ppdate))
	(setq long_1 (max bw L0 (/ Lc 2)))
        (setq long_1 (float(* (fix(/ (+ long_1 49) 50)) 50)))
       (setq long_11 (max bw L0 Lc))
	(setq long_2 (max d_wall_long3 L0 (/ Lc 2)))
        (setq long_2 (float(* (fix(/ (+ long_2 49) 50)) 50)))
       (setq long_22 (max d_wall_long3 L0 Lc))
	(setq d_wall (- d_wall_long1 (+ long_1 long_2)))
      
	(setq d_wall_LC (- d_wall_long1 (+ long_11 long_22)))
	(if (= (car L1_P1) (car L1_P2));;;如果是"真"则平行Y轴
	  (progn
	    (if (< (car L1_P0) (car L1_P1))
	      (setq k (1- 0))
	      (setq k 1)
	      )
	    (setq L2_P1X (+ (car L1_P1) (* k long_1)))
	    (setq L2_P1Y (cadr L1_P1))
            (setq L2_P1 (list L2_P1X L2_P1Y))
            (setq L2_P2X (+ (car L1_P2) (* k long_1)))
            (setq L2_P2Y (cadr L1_P2))
            (setq L2_P2 (list L2_P2X L2_P2Y))
	    (setq L5_P1X (+ (car L1_P1) (* k long_11)))
	    (setq L5_P1Y (cadr L1_P1))
            (setq L5_P1 (list L5_P1X L5_P1Y))
            (setq L5_P2X (+ (car L1_P2) (* k long_11)))
            (setq L5_P2Y (cadr L1_P2))
            (setq L5_P2 (list L5_P2X L5_P2Y))
	    (setq p99 (inters L5_P1 L5_P2 (nth 4 ppdate) (nth 5 ppdate)))
	    (IF (/= P99 nil)
	      (PROGN
		(setq long_11c (- d_wall_long1 (max d_wall_long3 L0 Lc)))
		(setq L5_P1X (+ (car L4_P1) (* (* (1- 0) k) long_11c)))
	        (setq L5_P1Y (cadr L4_P1))
                (setq L5_P1 (list L5_P1X L5_P1Y))
                (setq L5_P2X (+ (car L4_P2) (* (* (1- 0) k) long_11c)))
                (setq L5_P2Y (cadr L4_P2))
                (setq L5_P2 (list L5_P2X L5_P2Y))
		(setq d_wall_LC (- d_wall_long1 (+ long_11c long_22)))
		)
	      )
	    (setq p88 (inters L2_P1 L2_P2 (nth 4 ppdate) (nth 5 ppdate)))
	    (IF (/= P88 nil)
	      (PROGN
		(setq long_1c (- d_wall_long1 (max d_wall_long3 L0 (/ Lc 2))))
		(setq L2_P1X (+ (car L4_P1) (* (* (1- 0) k) long_1c)))
	        (setq L2_P1Y (cadr L4_P1))
                (setq L2_P1 (list L2_P1X L2_P1Y))
                (setq L2_P2X (+ (car L4_P2) (* (* (1- 0) k) long_1c)))
                (setq L2_P2Y (cadr L4_P2))
                (setq L2_P2 (list L2_P2X L2_P2Y))
		(setq d_wall (- d_wall_long1 (+ long_1c long_2)))
		)
	      )
	       
	    
            (setq L3_P1X (+ (car L4_P1) (* (* k (1- 0)) long_2)))
            (setq L3_P1y (cadr L4_P1))
            (setq L3_P2x (+ (car L4_P2) (* (* k (1- 0)) long_2)))
            (setq L3_P2y (cadr L4_P2))
            (setq L3_P1 (list L3_P1x L3_P1y))
            (setq L3_P2 (list L3_P2x L3_P2y))
	     (setq L6_P1X (+ (car L4_P1) (* (* k (1- 0)) long_22)))
            (setq L6_P1y (cadr L4_P1))
            (setq L6_P2x (+ (car L4_P2) (* (* k (1- 0)) long_22)))
            (setq L6_P2y (cadr L4_P2))
            (setq L6_P1 (list L6_P1x L6_P1y))
            (setq L6_P2 (list L6_P2x L6_P2y))
	    
	)
     ;;;(= (car L1_P1) (car L1_P2));;;如果是"假"则平行x轴
      (progn
	(if (< (cadr L1_P0) (cadr L1_P1))
	  (setq k (1- 0))
	  (setq k 1)
	  )
	(setq L2_P1Y (+ (cadr L1_P1) (* k long_1)))
        (setq L2_P1X (car L1_P1))
        (setq L2_P1 (list L2_P1X L2_P1Y))
        (setq L2_P2Y (+ (cadr L1_P2) (* k long_1)))
        (setq L2_P2X (car L1_P2))
        (setq L2_P2 (list L2_P2X L2_P2Y))
	
        (setq L5_P1Y (+ (cadr L1_P1) (* k long_11)))
	(setq L5_P1X (car L1_P1))
        (setq L5_P1 (list L5_P1X L5_P1Y))
        (setq L5_P2y (+ (cadr L1_P2) (* k long_11)))
        (setq L5_P2x (car L1_P2))
        (setq L5_P2 (list L5_P2X L5_P2Y))

        (setq p99 (inters L5_P1 L5_P2 (nth 4 ppdate) (nth 5 ppdate)))
	(IF (/= P99 nil)
	      (PROGN
		(setq long_11c (- d_wall_long1 (max d_wall_long3 L0 Lc)))
		(setq L5_P1y (+ (cadr L4_P1) (* (* (1- 0) k) long_11c)))
	        (setq L5_P1x (car L4_P1))
                (setq L5_P1 (list L5_P1X L5_P1Y))
                (setq L5_P2y (+ (cadr L4_P2) (* (* (1- 0) k) long_11c)))
                (setq L5_P2x (car L4_P2))
                (setq L5_P2 (list L5_P2X L5_P2Y))
		(setq d_wall_LC (- d_wall_long1 (+ long_11c long_22)))
		)
	      )
	    (setq p88 (inters L2_P1 L2_P2 (nth 4 ppdate) (nth 5 ppdate)))
	    (IF (/= P88 nil)
	      (PROGN
		(setq long_1c (- d_wall_long1 (max d_wall_long3 L0 (/ Lc 2))))
		(setq L2_P1y (+ (cadr L4_P1) (* (* (1- 0) k) long_1c)))
	        (setq L2_P1x (car L4_P1))
                (setq L2_P1 (list L2_P1X L2_P1Y))
                (setq L2_P2y (+ (cadr L4_P2) (* (* (1- 0) k) long_1c)))
                (setq L2_P2x (car L4_P2))
                (setq L2_P2 (list L2_P2X L2_P2Y))
		(setq d_wall (- d_wall_long1 (+ long_1c long_2)))
		
		)
	      )


	
        (setq L3_P1y (+ (cadr L4_P1) (* (* k (1- 0)) long_2)))
        (setq L3_P1x (car L14_P1))
        (setq L3_P2y (+ (cadr L4_P2) (* (* k (1- 0)) long_2)))
        (setq L3_P2x (car L4_P2))
        (setq L3_P1 (list L3_P1x L3_P1y))
        (setq L3_P2 (list L3_P2x L3_P2y))
	(setq L6_P1y (+ (cadr L4_P1) (* (* k (1- 0)) long_22)))
        (setq L6_P1x (car L4_P1))
        (setq L6_P2y (+ (cadr L4_P2) (* (* k (1- 0)) long_22)))
        (setq L6_P2x (car L4_P2))
        (setq L6_P1 (list L6_P1x L6_P1y))
        (setq L6_P2 (list L6_P2x L6_P2y))
	
	
	)
	  )
       
	(if (and (>= d_wall d_wall_0)) ;;;d_wall表示2个边缘构件中间部分的墙长，h为另外一个方向的墙厚
	  (progn
	    (command "line" L2_P1 L2_P2 "" "")
            (setq e1 (entlast))
            (setq e1_list (entget e1))
            (setq e1_list (subst (cons 10 L2_P1) (assoc 10 e1_list) e1_list))
            (setq e1_list (subst (cons 11 L2_P2) (assoc 11 e1_list) e1_list))
            (setq e1_list (subst (cons 8 "WALL_DETL") (assoc 8 e1_list) e1_list))
            (entmod e1_list)
            (setq O1 (inters L1_P1 L2_P2 L1_P2 L2_P1))  ;;;求出内部的点，然后进行填充
            (command "_bhatch" "p" "SOLID" O1 "")
            (setq e1 (entlast))
            (setq e1_list (entget e1))
            (setq e1_list (subst (cons 8 "WC_HATCH") (assoc 8 e1_list) e1_list))
            (entmod e1_list)
            (command "line" L3_P1 L3_P2 "" "")
            (setq e1 (entlast))
            (setq e1_list (entget e1))
            (setq e1_list (subst (cons 10 L3_P1) (assoc 10 e1_list) e1_list))
            (setq e1_list (subst (cons 11 L3_P2) (assoc 11 e1_list) e1_list))
            (setq e1_list (subst (cons 8 "WALL_DETL") (assoc 8 e1_list) e1_list))
            (entmod e1_list)
	    (setq O2 (inters L4_P1 L3_P2 L4_P2 L3_P1))  ;;;求出内部的点，然后进行填充
	    (command "_bhatch" "p" "SOLID" O2 "")
            (setq e1 (entlast))
            (setq e1_list (entget e1))
            (setq e1_list (subst (cons 8 "WC_HATCH") (assoc 8 e1_list) e1_list))
            (entmod e1_list)
	    
	    (if (and (>= d_wall_LC d_wall_0)) ;;;d_wall表示2个边缘构件中间部分的墙长，h为另外一个方向的墙厚
	      (progn
		 (command "line" L5_P1 L5_P2 "" "")
                 (setq e1 (entlast))
                 (setq e1_list (entget e1))
                 (setq e1_list (subst (cons 10 L5_P1) (assoc 10 e1_list) e1_list))
                 (setq e1_list (subst (cons 11 L5_P2) (assoc 11 e1_list) e1_list))
                 (setq e1_list (subst (cons 8 "WALL_DETL") (assoc 8 e1_list) e1_list))
                 (entmod e1_list)
                 (setq O1 (inters L5_P1 L2_P2 L5_P2 L2_P1))  ;;;求出内部的点，然后进行填充
            (command "_bhatch" "p" "ansi31" "400" "0" O1 "")
            (setq e1 (entlast))
            (setq e1_list (entget e1))
            (setq e1_list (subst (cons 8 "Wall_DETL_HATCH") (assoc 8 e1_list) e1_list))
            (entmod e1_list)
            (command "line" L6_P1 L6_P2 "" "")
            (setq e1 (entlast))
            (setq e1_list (entget e1))
            (setq e1_list (subst (cons 10 L6_P1) (assoc 10 e1_list) e1_list))
            (setq e1_list (subst (cons 11 L6_P2) (assoc 11 e1_list) e1_list))
            (setq e1_list (subst (cons 8 "WALL_DETL") (assoc 8 e1_list) e1_list))
            (entmod e1_list)
	    (setq O2 (inters L3_P1 L6_P2 L3_P2 L6_P1))  ;;;求出内部的点，然后进行填充
	    (command "_bhatch" "p" "ansi31" "400" "0" O2 "")
            (setq e1 (entlast))
            (setq e1_list (entget e1))
            (setq e1_list (subst (cons 8 "Wall_DETL_HATCH") (assoc 8 e1_list) e1_list))
            (entmod e1_list)
		)
	      (progn
		(setq O2 (inters L2_P1 L3_P2 L2_P2 L3_P1))  ;;;求出内部的点，然后进行填充
	    (command "_bhatch" "p" "ansi31" "400" "0" O2 "")
            (setq e1 (entlast))
            (setq e1_list (entget e1))
            (setq e1_list (subst (cons 8 "Wall_DETL_HATCH") (assoc 8 e1_list) e1_list))
            (entmod e1_list)
		)
	      )
	    )
	  )
       );progn1
    );”I“型IF结束
      (if (<= bf (* 4 d_wall_long3));;;;非”I“型；；；还有个轴压比0.3的判断
	(progn
	  (setq ct 0)
      (repeat 2
	(if (= ct 1)
	  (progn
	    (setq ppdate (reverse ppdate))
	    (setq pp_dist_date (reverse pp_dist_date))
	    )
	  )
	  (setq L1_P1 (nth 1 ppdate))
    (setq L1_P2 (nth 2 ppdate))
    (setq L1_P0 (nth 3 ppdate))  ;;;;移动方向判定点
    (setq bw (nth 1 pp_dist_date))
    (setq bf (nth 4 pp_dist_date))
    (setq d_wall_long1 (nth 0 pp_dist_date))
    (setq d_wall_long2 (nth 2 pp_dist_date))
    (setq d_wall_long3 (nth 5 pp_dist_date))
	  (if (and(>= bf 300) (>= d_wall_long3 300) (< d_wall_long3 (* 4 bf)) (> d_wall_long3 (/ bf 4)))
      (setq wc0 "c0")
      (setq wc0 "w0")
	    )
	  (if (= wc0 "c0")
      (setq wc_h (/ (* 2 (max bf d_wall_long3)) 3))
      (setq wc_h d_wall_long3)
	    )

    ;;下面判定是否按有翼墙查表。
	  (if (< wc_h (* 3 bw))
      (setq wc "0");;;不按有翼墙查表。
      (setq wc "1");;;按有翼墙查表。
	    )
	  (IF (= WC "1")
    (setq Lck (- Lck (/ (float 5) 100)))
	    )
    (setq Lc (* d_wall_long1 Lck))
    (setq Lc (float(* (fix(/ (+ LC 49) 50)) 50)))
	(IF (= WC "1")
    (setq Lck (+ Lck (/ (float 5) 100)))
	    );;;;;;;将Lck还原，已经不影响程序的，LC已经求出来。
    (setq long_1 (max bw L0 (/ Lc 2)))
    (setq long_1 (float(* (fix(/ (+ long_1 49) 50)) 50)))
    (setq long_LC1 (max bw L0 Lc))
    (setq long_2 (- d_wall_long1 (max (+ bw bf) (+ bw 300))))
    (setq long_2 (float(* (fix(/ (+ long_2 49) 50)) 50)))
    (setq long_LC2 (- d_wall_long1 (max (+ bw bf) (+ bw 300) LC)))
    (setq d_wall (- long_2 long_1))
    (setq d_wall_LC (- long_LC2 long_LC1))
	  (if (= (car L1_P1) (car L1_P2));;;如果是"真"则平行Y轴
	    (progn
	      (if (< (car L1_P0) (car L1_P1))
		(setq k (1- 0))
		(setq k 1)
		)
	      (setq L2_P1X (+ (car L1_P1) (* k long_1)))
	      (setq L2_P1Y (cadr L1_P1))
              (setq L2_P1 (list L2_P1X L2_P1Y))
              (setq L2_P2X (+ (car L1_P2) (* k long_1)))
              (setq L2_P2Y (cadr L1_P2))
              (setq L2_P2 (list L2_P2X L2_P2Y))
	      
	      (setq L4_P1X (+ (car L1_P1) (* k long_LC1)))
	      (setq L4_P1Y (cadr L1_P1))
              (setq L4_P1 (list L4_P1X L4_P1Y))
              (setq L4_P2X (+ (car L1_P2) (* k long_LC1)))
              (setq L4_P2Y (cadr L1_P2))
              (setq L4_P2 (list L4_P2X L4_P2Y))
	;;;;
              (setq L3_P1X (+ (car L1_P1) (* k long_2)))
              (setq L3_P1y (cadr L1_P1))
              (setq L3_P2x (+ (car L1_P2) (* k long_2)))
              (setq L3_P2y (cadr L1_P2))
              (setq L3_P1 (list L3_P1x L3_P1y))
              (setq L3_P2 (list L3_P2x L3_P2y))
	      
	      (setq L5_P1X (+ (car L1_P1) (* k long_2)))
              (setq L5_P1y (cadr L1_P1))
              (setq L5_P2x (+ (car L1_P2) (* k long_2)))
              (setq L5_P2y (cadr L1_P2))
              (setq L5_P1 (list L5_P1x L5_P1y))
              (setq L5_P2 (list L5_P2x L5_P2y))
	      )
     ;;;(= (car L1_P1) (car L1_P2));;;如果是"假"则平行x轴
	    (progn
	      (if (< (cadr L1_P0) (cadr L1_P1))
		(setq k (1- 0))
	        (setq k 1)
		)
	      (setq L2_P1Y (+ (cadr L1_P1) (* k long_1)))
              (setq L2_P1X (car L1_P1))
              (setq L2_P1 (list L2_P1X L2_P1Y))
              (setq L2_P2Y (+ (cadr L1_P2) (* k long_1)))
              (setq L2_P2X (car L1_P2))
              (setq L2_P2 (list L2_P2X L2_P2Y))

	      (setq L4_P1Y (+ (cadr L1_P1) (* k long_LC1)))
              (setq L4_P1X (car L1_P1))
              (setq L4_P1 (list L4_P1X L4_P1Y))
              (setq L4_P2Y (+ (cadr L1_P2) (* k long_LC1)))
              (setq L4_P2X (car L1_P2))
              (setq L4_P2 (list L4_P2X L4_P2Y))

	      
              (setq L3_P1y (+ (cadr L1_P1) (* k long_2)))
              (setq L3_P1x (car L1_P1))
              (setq L3_P2y (+ (cadr L1_P2) (* k long_2)))
              (setq L3_P2x (car L1_P2))
              (setq L3_P1 (list L3_P1x L3_P1y))
              (setq L3_P2 (list L3_P2x L3_P2y))

	      (setq L5_P1y (+ (cadr L1_P1) (* k long_LC2)))
              (setq L5_P1x (car L1_P1))
              (setq L5_P2y (+ (cadr L1_P2) (* k long_LC2)))
              (setq L5_P2x (car L1_P2))
              (setq L5_P1 (list L5_P1x L5_P1y))
              (setq L5_P2 (list L5_P2x L5_P2y))
	      )
	    )
	  (if (and (>= d_wall d_wall_0) (>= d_wall_long2 (- long_2 long_1)));;画构件if
	    (progn
      (command "line" L2_P1 L2_P2 "" "")
      (setq e1 (entlast))
      (setq e1_list (entget e1))
      (setq e1_list (subst (cons 10 L2_P1) (assoc 10 e1_list) e1_list))
      (setq e1_list (subst (cons 11 L2_P2) (assoc 11 e1_list) e1_list))
      (setq e1_list (subst (cons 8 "WALL_DETL") (assoc 8 e1_list) e1_list))
      (entmod e1_list)
      (setq O1 (inters L1_P1 L2_P2 L1_P2 L2_P1))  ;;;求出内部的点，然后进行填充
      (command "_bhatch" "p" "SOLID" O1 "")
      (setq e1 (entlast))
      (setq e1_list (entget e1))
      (setq e1_list (subst (cons 8 "WC_HATCH") (assoc 8 e1_list) e1_list))
      (entmod e1_list)
      (command "line" L3_P1 L3_P2 "" "")
      (setq e1 (entlast))
      (setq e1_list (entget e1))
      (setq e1_list (subst (cons 10 L3_P1) (assoc 10 e1_list) e1_list))
      (setq e1_list (subst (cons 11 L3_P2) (assoc 11 e1_list) e1_list))
      (setq e1_list (subst (cons 8 "WALL_DETL") (assoc 8 e1_list) e1_list))
      (entmod e1_list)
      (if (>= d_wall_LC d_wall_0)
	(progn
	  (if (> LC long_1)
	(progn
	  (command "line" L4_P1 L4_P2 "" "")
          (setq e1 (entlast))
          (setq e1_list (entget e1))
          (setq e1_list (subst (cons 10 L4_P1) (assoc 10 e1_list) e1_list))
          (setq e1_list (subst (cons 11 L4_P2) (assoc 11 e1_list) e1_list))
          (setq e1_list (subst (cons 8 "WALL_DETL") (assoc 8 e1_list) e1_list))
          (entmod e1_list)
          (setq O1 (inters L4_P1 L2_P2 L4_P2 L2_P1))  ;;;求出内部的点，然后进行填充
          (command "_bhatch" "p" "ansi31" "30" "0" O1 "")
          (setq e1 (entlast))
          (setq e1_list (entget e1))
          (setq e1_list (subst (cons 8 "Wall_DETL_HATCH") (assoc 8 e1_list) e1_list))
          (entmod e1_list)
	  )
	    )
(if (> LC (max (+ bw bf) (+ 300 bf)))
	(progn
	  (command "line" L5_P1 L5_P2 "" "")
          (setq e1 (entlast))
          (setq e1_list (entget e1))
          (setq e1_list (subst (cons 10 L5_P1) (assoc 10 e1_list) e1_list))
          (setq e1_list (subst (cons 11 L5_P2) (assoc 11 e1_list) e1_list))
          (setq e1_list (subst (cons 8 "WALL_DETL") (assoc 8 e1_list) e1_list))
          (entmod e1_list)
          (setq O1 (inters L5_P1 L3_P2 L5_P2 L3_P1))  ;;;求出内部的点，然后进行填充
          (command "_bhatch" "p" "ansi31" "30" "0" O1 "")
          (setq e1 (entlast))
          (setq e1_list (entget e1))
          (setq e1_list (subst (cons 8 "Wall_DETL_HATCH") (assoc 8 e1_list) e1_list))
          (entmod e1_list)
	  )
	    )

	  
	  )
	(progn
	  (setq O1 (inters L3_P1 L2_P2 L3_P2 L2_P1))  ;;;求出内部的点，然后进行填充
          (command "_bhatch" "p" "ansi31" "30" "0" O1 "")
          (setq e1 (entlast))
          (setq e1_list (entget e1))
          (setq e1_list (subst (cons 8 "Wall_DETL_HATCH") (assoc 8 e1_list) e1_list))
          (entmod e1_list)
	  )
	)
      )
    (progn
      ;;;;无内容，因为”另外翼墙的约束构件边线没有画出“!!!!
      )
    );;画构件if
	(setq ct (+ ct 1))
	)
	  (setq p_x (list (/ (+ (car(nth 0 ppdate)) (car(nth 3  ppdate))) 2) (/ (+ (cadr(nth 0 ppdate)) (cadr(nth 3  ppdate))) 2)))
  (command "_bhatch" "p" "SOLID" p_x "")
  (setq e1 (entlast))
  (setq e1_list (entget e1))
  (setq e1_list (subst (cons 8 "WC_HATCH") (assoc 8 e1_list) e1_list))
  (entmod e1_list)
	  )
	)
      )
    )
  (PRIN1)
  )
