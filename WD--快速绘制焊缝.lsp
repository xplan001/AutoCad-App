(DEFUN C:WD ()
        (setq cl (getvar "clayer"))
        (Setvar "cmdecho" 0)
        (COMMAND "LAYER" "M" "WELD" "C" "M" "" "LT" "CONTINUOUS" "" "")
        (SETQ S (GETVAR "SNAPANG"))
        (SETQ P1 (GETPOINT "\nSTART POINT: "))
        (SETQ P2 (GETPOINT P1 "\nEND POINT: "))
        (SETQ Z (GETREAL "\nWELD SIZE: "))
        (SETQ P3 (POLAR P1 (ANGLE P1 P2) (* 2 Z)))
        (setq osm (getvar "osmode"))
        (setvar "osmode" 0)
        (COMMAND "ARC" P1 "E" P3 "A" 180)
        (SETQ P4 (POLAR P3 (- (ANGLE P1 P2) (* 120 (/ PI 180))) Z))
        (SETQ N (- (/ (DISTANCE P1 P2) Z) 2))
        (COMMAND "ARC" P4 "C" P3 "A" 120)        
        (SETQ X 1)
        (WHILE (<= X N)(SETQ X (+ X 1)))
        (SETVAR "SNAPANG" (ANGLE P1 P2))
        (COMMAND "ARRAY" "LAST" "" "R" "" (- X 1) Z)
        (SETVAR "SNAPANG" 0)
        (PRINC)
        (command ".layer" "set" cl "")
        (setvar "osmode" 171)
)
