;;电脑内字体少而打开别人的图纸字体特别多怎么办？在文字样式中一个一个修改，这当然麻烦，送一个;;自编的小程序给你。这种又没技术含量又很烦的修改让电脑去做吧。
(defun c:ft (/ elist nm en cn enl)
(setq elist (tblnext "STYLE" T))
(while (/= elist nil)
(setq nm (cdr (assoc 2 elist))
en (cdr (assoc 3 elist)) 
cn (cdr (assoc 4 elist))
enl (strlen en)
)
(if (and 
(/= en nil)
(= cn nil)
(= (findfile en) nil)
(= (strcase (substr en (- enl 2))) "SHX")
) 
(command "_style" nm "romans.shx" "0.0" "0.8" "" "" "" "")
)
(if (and 
(/= cn nil)
(= (findfile cn) nil)
) 
(command "_style" nm "romans.shx,hztxt.shx" "0.0" "0.8" "" "" "" "")
)
(setq elist (tblnext "STYLE"))
)
)
