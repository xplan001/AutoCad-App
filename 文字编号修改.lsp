;文字编号修改
(defun c:wzxg()
(setq ff(getint "\n请输入修改起点数:"))
(setq txtf(getint "\n请输入后缀修改数字的个数:"))
(setq wz (Vlax-Ename->Vla-Object (car (entsel))))
(setq i ff)
(while (/= wz nil)
       (Setq old_wz (Vlax-Get wz 'TextString ))
       (setq sv (- (strlen old_wz)txtf))
       (setq *str(strcat (substr old_wz 1 sv) (rtos i 2 1)))
       (Setq new_wz (Vlax-Put-Property wz 'TextString *str))
       (entmod new_wz)
       (setq i(1+ i))
       (setq wz (Vlax-Ename->Vla-Object (car (entsel))))
       )
       )
