(defun c:ptx(/)
  (setvar "osmode" 0)
  (setvar "osmode" 1)
  (princ
    "\n请选择两个点(建筑面层到建筑面层）by.zjm")
  (setq a (getpoint))
  (setq b (getpoint a))
  (setvar "osmode" 0)
  (setq pda (car a))(setq pdb (car b))
  (if (< pda pdb)
    (progn
      (setq c b)
      (setq b a)
      (setq a c)
      )
    )
  (setq px1 (+ 300(car a)))(setq py1 (cadr a))
  (setq px2 px1)(setq py2 (+ 2200 (cadr a)))
  (setq px3 (car a)) (setq py3 py2)
  (setq px4 (car b)) (setq py4 (+ 2200 (cadr b)))
  (setq px5 (- (car b) 300))(setq py5 (+ 2200 (cadr b)))
  (setq px6 px5)(setq py6 (cadr b))
  (setq p1 (list px1 py1))
  (setq p2 (list px2 py2))
  (setq p3 (list px3 py3))
  (setq p4 (list px4 py4))
  (setq p5 (list px5 py5))
  (setq p6 (list px6 py6))
  (command "pline" a "w" 0 0 p1 p2 p3 p4 p5 p6 b "c")
(setq ty (entlast))
(setq ent (entget ty))
(setq tc1 (assoc 8 ent))
(setq tc2 (cons 8 "D1"))
(setq tc (subst tc2 tc1 ent))
(entmod tc)
  (princ)
  )
