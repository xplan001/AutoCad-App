(defun c:tcs (/ clayer1 ss i)
	(vl-load-com)
  (command "undo" "be")
   (setvar "CMDECHO" 0)
(setvar "hpassoc" 1);填充关联
  (setq clayer1 (getvar "clayer"))
  ;(if (tblsearch "layer" "实体填充")
    (command "layer" "M" "实体填充" "C" "9" "" "LT" "CONTINUOUS" "" "");设置一个标注图层;
 ; )
	(setq ss (ssget '((0 . "LWPOLYLINE"))))
	(setq i -1)
	(repeat (sslength ss)
	(command ".-bhatch" "p" "solid"  "a"  "a" "" "" "s" (ssname ss (setq i (1+ i))) "" ""  )
	)
  (setvar "clayer" clayer1)
  (princ)
  (command "undo" "e")
	(princ "\n 批量实体填充程序，命令:tcs 【编写者：执著  】")
	(princ "\n 【填充命令、图层、样式及比例可根据个人需要自行修改】")
   (setvar "CMDECHO" 1)
	(princ)
)
